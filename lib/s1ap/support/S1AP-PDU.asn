-- **************************************************************
--
-- Elementary Procedure definitions
--
-- **************************************************************


S1AP-PDU-Descriptions  { 
itu-t (0) identified-organization (4) etsi (0) mobileDomain (0) 
eps-Access (21) modules (3) s1ap (1) version1 (1) s1ap-PDU-Descriptions (0)}


DEFINITIONS AUTOMATIC TAGS ::= 


BEGIN


-- **************************************************************
--
-- IE parameter types from other modules.
--
-- **************************************************************


IMPORTS
        S1AP-Criticality,
        S1AP-ProcedureCode
FROM S1AP-CommonDataTypes


        S1AP-CellTrafficTrace,
        S1AP-DeactivateTrace,
        S1AP-DownlinkUEAssociatedLPPaTransport,
        S1AP-DownlinkNASTransport,
        S1AP-DownlinkNonUEAssociatedLPPaTransport,
        S1AP-DownlinkS1cdma2000tunneling,
        S1AP-ENBDirectInformationTransfer,
        S1AP-ENBStatusTransfer,
        S1AP-ENBConfigurationUpdate,
        S1AP-ENBConfigurationUpdateAcknowledge,
        S1AP-ENBConfigurationUpdateFailure,
        S1AP-ErrorIndication,
        S1AP-HandoverCancel,
        S1AP-HandoverCancelAcknowledge,
        S1AP-HandoverCommand,
        S1AP-HandoverFailure,
        S1AP-HandoverNotify,
        S1AP-HandoverPreparationFailure,
        S1AP-HandoverRequest,
        S1AP-HandoverRequestAcknowledge,
        S1AP-HandoverRequired,
        S1AP-InitialContextSetupFailure,
        S1AP-InitialContextSetupRequest,
        S1AP-InitialContextSetupResponse,
        S1AP-InitialUEMessage,
        S1AP-KillRequest,
        S1AP-KillResponse,
        S1AP-LocationReportingControl,
        S1AP-LocationReportingFailureIndication,
        S1AP-LocationReport,
        S1AP-MMEConfigurationUpdate,
        S1AP-MMEConfigurationUpdateAcknowledge,
        S1AP-MMEConfigurationUpdateFailure,
        S1AP-MMEDirectInformationTransfer,
        S1AP-MMEStatusTransfer,
        S1AP-NASNonDeliveryIndication,
        S1AP-OverloadStart,
        S1AP-OverloadStop,
        S1AP-Paging,
        S1AP-PathSwitchRequest,
        S1AP-PathSwitchRequestAcknowledge,
        S1AP-PathSwitchRequestFailure,        
        S1AP-PrivateMessage,
        S1AP-Reset,
        S1AP-ResetAcknowledge,
        S1AP-S1SetupFailure,
        S1AP-S1SetupRequest,
        S1AP-S1SetupResponse,
        S1AP-E-RABModifyRequest,
        S1AP-E-RABModifyResponse,
        S1AP-E-RABReleaseCommand,
        S1AP-E-RABReleaseResponse,
        S1AP-E-RABReleaseIndication,
        S1AP-E-RABSetupRequest,
        S1AP-E-RABSetupResponse,
        S1AP-TraceFailureIndication,
        S1AP-TraceStart,
        S1AP-UECapabilityInfoIndication,
        S1AP-UEContextModificationFailure,
        S1AP-UEContextModificationRequest,
        S1AP-UEContextModificationResponse,
        S1AP-UEContextReleaseCommand,
        S1AP-UEContextReleaseComplete,
        S1AP-UEContextReleaseRequest,
        S1AP-UplinkUEAssociatedLPPaTransport,
        S1AP-UplinkNASTransport,
        S1AP-UplinkNonUEAssociatedLPPaTransport,
        S1AP-UplinkS1cdma2000tunneling,
        S1AP-WriteReplaceWarningRequest,
        S1AP-WriteReplaceWarningResponse,
        S1AP-ENBConfigurationTransfer,
        S1AP-MMEConfigurationTransfer




FROM S1AP-PDU-Contents
        
        id-CellTrafficTrace,
        id-DeactivateTrace,
        id-downlinkUEAssociatedLPPaTransport,
        id-downlinkNASTransport,
        id-downlinkNonUEAssociatedLPPaTransport,
        id-DownlinkS1cdma2000tunneling,
        id-eNBStatusTransfer,
        id-ErrorIndication,
        id-HandoverCancel,
        id-HandoverNotification,
        id-HandoverPreparation,
        id-HandoverResourceAllocation,
        id-InitialContextSetup,
        id-initialUEMessage,
        id-ENBConfigurationUpdate,
        id-Kill,
        id-LocationReportingControl,
        id-LocationReportingFailureIndication,
        id-LocationReport,
        id-eNBDirectInformationTransfer,
        id-MMEConfigurationUpdate,
        id-MMEDirectInformationTransfer,
        id-MMEStatusTransfer,
        id-NASNonDeliveryIndication,
        id-OverloadStart,
        id-OverloadStop,
        id-Paging,
        id-PathSwitchRequest,
        id-PrivateMessage,
        id-Reset,
        id-S1Setup,
        id-E-RABModify,
        id-E-RABRelease,
        id-E-RABReleaseIndication,
        id-E-RABSetup,
        id-TraceFailureIndication,
        id-TraceStart,
        id-UECapabilityInfoIndication,
        id-UEContextModification,
        id-UEContextRelease,
        id-UEContextReleaseRequest,
        id-uplinkUEAssociatedLPPaTransport,
        id-uplinkNASTransport,
        id-uplinkNonUEAssociatedLPPaTransport,
        id-UplinkS1cdma2000tunneling,
        id-WriteReplaceWarning,
        id-eNBConfigurationTransfer,
        id-MMEConfigurationTransfer
FROM S1AP-Constants;




-- **************************************************************
--
-- Interface Elementary Procedure Class
--
-- **************************************************************


S1AP-ELEMENTARY-PROCEDURE ::= CLASS {
        &S1AP-InitiatingMessage                                ,
        &S1AP-SuccessfulOutcome                                OPTIONAL,
        &S1AP-UnsuccessfulOutcome                                OPTIONAL,
        &procedureCode                        S1AP-ProcedureCode         UNIQUE,
        &criticality                        S1AP-Criticality         DEFAULT ignore
}
WITH SYNTAX {
        INITIATING MESSAGE                        &S1AP-InitiatingMessage
        [SUCCESSFUL OUTCOME                        &S1AP-SuccessfulOutcome]
        [UNSUCCESSFUL OUTCOME                &S1AP-UnsuccessfulOutcome]
        PROCEDURE CODE                                &procedureCode
        [CRITICALITY                                &criticality]
}


-- **************************************************************
--
-- Interface PDU Definition
--
-- **************************************************************


S1AP-PDU ::= CHOICE {
        initiatingMessage        S1AP-InitiatingMessage,
        successfulOutcome        S1AP-SuccessfulOutcome,
        unsuccessfulOutcome        S1AP-UnsuccessfulOutcome,
        ...
}


S1AP-InitiatingMessage ::= SEQUENCE {
        procedureCode        S1AP-ELEMENTARY-PROCEDURE.&procedureCode        ({S1AP-ELEMENTARY-PROCEDURES}),
        criticality        S1AP-ELEMENTARY-PROCEDURE.&criticality                        ({S1AP-ELEMENTARY-PROCEDURES}{@procedureCode}),
        value                S1AP-ELEMENTARY-PROCEDURE.&S1AP-InitiatingMessage        ({S1AP-ELEMENTARY-PROCEDURES}{@procedureCode})
}


S1AP-SuccessfulOutcome ::= SEQUENCE {
        procedureCode        S1AP-ELEMENTARY-PROCEDURE.&procedureCode        ({S1AP-ELEMENTARY-PROCEDURES}),
        criticality        S1AP-ELEMENTARY-PROCEDURE.&criticality                        ({S1AP-ELEMENTARY-PROCEDURES}{@procedureCode}),
        value                S1AP-ELEMENTARY-PROCEDURE.&S1AP-SuccessfulOutcome        ({S1AP-ELEMENTARY-PROCEDURES}{@procedureCode})
}


S1AP-UnsuccessfulOutcome ::= SEQUENCE {
        procedureCode        S1AP-ELEMENTARY-PROCEDURE.&procedureCode        ({S1AP-ELEMENTARY-PROCEDURES}),
        criticality        S1AP-ELEMENTARY-PROCEDURE.&criticality                        ({S1AP-ELEMENTARY-PROCEDURES}{@procedureCode}),
        value                S1AP-ELEMENTARY-PROCEDURE.&S1AP-UnsuccessfulOutcome        ({S1AP-ELEMENTARY-PROCEDURES}{@procedureCode})
}


-- **************************************************************
--
-- Interface Elementary Procedure List
--
-- **************************************************************


S1AP-ELEMENTARY-PROCEDURES S1AP-ELEMENTARY-PROCEDURE ::= {
        S1AP-ELEMENTARY-PROCEDURES-CLASS-1                |
        S1AP-ELEMENTARY-PROCEDURES-CLASS-2,        
        ...
}




S1AP-ELEMENTARY-PROCEDURES-CLASS-1 S1AP-ELEMENTARY-PROCEDURE ::= {
        handoverPreparation                                |
        handoverResourceAllocation                |
        pathSwitchRequest                                 |
        e-RABSetup                                                |
        e-RABModify                                                |
        e-RABRelease                                        |
        initialContextSetup                                |
        handoverCancel                                        |
        kill                                                        |
        reset                                                        |
        s1Setup                                                        |
        uEContextModification                        |
        uEContextRelease                                |
        eNBConfigurationUpdate                        |
        mMEConfigurationUpdate                        |
        writeReplaceWarning                                ,
        ...
}


S1AP-ELEMENTARY-PROCEDURES-CLASS-2 S1AP-ELEMENTARY-PROCEDURE ::= {        
        handoverNotification                        |
        e-RABReleaseIndication                        |
        paging                                                         |
        downlinkNASTransport                        |
        initialUEMessage                                |
        uplinkNASTransport                                |
        errorIndication                                        |
        nASNonDeliveryIndication                |
        uEContextReleaseRequest                        |
        downlinkS1cdma2000tunneling                |
        uplinkS1cdma2000tunneling                |
        uECapabilityInfoIndication                |
        eNBStatusTransfer                                |
        mMEStatusTransfer                                |
        deactivateTrace                                        |
        traceStart                                                |
        traceFailureIndication                        |
        cellTrafficTrace                                |
        locationReportingControl                |
        locationReportingFailureIndication        |
        locationReport                                        |
        overloadStart                                        |
        overloadStop                                        |
        eNBDirectInformationTransfer        |
        mMEDirectInformationTransfer        |
        eNBConfigurationTransfer                |
        mMEConfigurationTransfer                |
        privateMessage                                        ,
        ...,
        downlinkUEAssociatedLPPaTransport        |
        uplinkUEAssociatedLPPaTransport        |
        downlinkNonUEAssociatedLPPaTransport        |
        uplinkNonUEAssociatedLPPaTransport
}


-- **************************************************************
--
-- Interface Elementary Procedures
--
-- **************************************************************


handoverPreparation S1AP-ELEMENTARY-PROCEDURE ::= {
        INITIATING MESSAGE        S1AP-HandoverRequired
        SUCCESSFUL OUTCOME        S1AP-HandoverCommand
        UNSUCCESSFUL OUTCOME        S1AP-HandoverPreparationFailure
        PROCEDURE CODE                        id-HandoverPreparation
        CRITICALITY                reject
}


handoverResourceAllocation S1AP-ELEMENTARY-PROCEDURE ::= {
        INITIATING MESSAGE        S1AP-HandoverRequest
        SUCCESSFUL OUTCOME        S1AP-HandoverRequestAcknowledge
        UNSUCCESSFUL OUTCOME        S1AP-HandoverFailure
        PROCEDURE CODE                        id-HandoverResourceAllocation
        CRITICALITY                reject
}


handoverNotification S1AP-ELEMENTARY-PROCEDURE ::= {
        INITIATING MESSAGE        S1AP-HandoverNotify
        PROCEDURE CODE                        id-HandoverNotification
        CRITICALITY                ignore
}


pathSwitchRequest S1AP-ELEMENTARY-PROCEDURE ::= {
        INITIATING MESSAGE        S1AP-PathSwitchRequest
        SUCCESSFUL OUTCOME        S1AP-PathSwitchRequestAcknowledge
        UNSUCCESSFUL OUTCOME        S1AP-PathSwitchRequestFailure
        PROCEDURE CODE                        id-PathSwitchRequest
        CRITICALITY                reject
}


e-RABSetup S1AP-ELEMENTARY-PROCEDURE ::= {
        INITIATING MESSAGE        S1AP-E-RABSetupRequest
        SUCCESSFUL OUTCOME        S1AP-E-RABSetupResponse
        PROCEDURE CODE                id-E-RABSetup
        CRITICALITY                reject
}


e-RABModify S1AP-ELEMENTARY-PROCEDURE ::= {
        INITIATING MESSAGE        S1AP-E-RABModifyRequest
        SUCCESSFUL OUTCOME        S1AP-E-RABModifyResponse
        PROCEDURE CODE                id-E-RABModify
        CRITICALITY                reject
}


e-RABRelease S1AP-ELEMENTARY-PROCEDURE ::= {
        INITIATING MESSAGE        S1AP-E-RABReleaseCommand
        SUCCESSFUL OUTCOME        S1AP-E-RABReleaseResponse
        PROCEDURE CODE                id-E-RABRelease
        CRITICALITY                reject
}


e-RABReleaseIndication S1AP-ELEMENTARY-PROCEDURE ::= {
        INITIATING MESSAGE        S1AP-E-RABReleaseIndication
        PROCEDURE CODE                id-E-RABReleaseIndication
        CRITICALITY                ignore
}


initialContextSetup S1AP-ELEMENTARY-PROCEDURE ::= {
        INITIATING MESSAGE        S1AP-InitialContextSetupRequest
        SUCCESSFUL OUTCOME        S1AP-InitialContextSetupResponse
        UNSUCCESSFUL OUTCOME S1AP-InitialContextSetupFailure
        PROCEDURE CODE                id-InitialContextSetup
        CRITICALITY                reject
}


uEContextReleaseRequest S1AP-ELEMENTARY-PROCEDURE ::= {
        INITIATING MESSAGE                S1AP-UEContextReleaseRequest
        PROCEDURE CODE                        id-UEContextReleaseRequest
        CRITICALITY                                ignore
}


paging S1AP-ELEMENTARY-PROCEDURE ::= {
        INITIATING MESSAGE        S1AP-Paging
        PROCEDURE CODE                id-Paging
        CRITICALITY                        ignore
}


downlinkNASTransport S1AP-ELEMENTARY-PROCEDURE ::= {
        INITIATING MESSAGE                S1AP-DownlinkNASTransport
        PROCEDURE CODE                        id-downlinkNASTransport
        CRITICALITY                                ignore
}


initialUEMessage S1AP-ELEMENTARY-PROCEDURE ::= {
        INITIATING MESSAGE                S1AP-InitialUEMessage
        PROCEDURE CODE                        id-initialUEMessage
        CRITICALITY                                ignore
}


uplinkNASTransport S1AP-ELEMENTARY-PROCEDURE ::= {
        INITIATING MESSAGE                S1AP-UplinkNASTransport
        PROCEDURE CODE                        id-uplinkNASTransport
        CRITICALITY                                ignore
}
nASNonDeliveryIndication S1AP-ELEMENTARY-PROCEDURE ::= {
        INITIATING MESSAGE                S1AP-NASNonDeliveryIndication
        PROCEDURE CODE                        id-NASNonDeliveryIndication
        CRITICALITY                                ignore
}


handoverCancel S1AP-ELEMENTARY-PROCEDURE ::= {
        INITIATING MESSAGE        S1AP-HandoverCancel
        SUCCESSFUL OUTCOME        S1AP-HandoverCancelAcknowledge
        PROCEDURE CODE                        id-HandoverCancel
        CRITICALITY                reject
}


reset S1AP-ELEMENTARY-PROCEDURE ::= {
        INITIATING MESSAGE        S1AP-Reset
        SUCCESSFUL OUTCOME        S1AP-ResetAcknowledge
        PROCEDURE CODE                id-Reset
        CRITICALITY                        reject
}


errorIndication S1AP-ELEMENTARY-PROCEDURE ::= {
        INITIATING MESSAGE        S1AP-ErrorIndication
        PROCEDURE CODE                id-ErrorIndication
        CRITICALITY                ignore
}


s1Setup S1AP-ELEMENTARY-PROCEDURE ::= {
        INITIATING MESSAGE                S1AP-S1SetupRequest
        SUCCESSFUL OUTCOME                S1AP-S1SetupResponse
        UNSUCCESSFUL OUTCOME         S1AP-S1SetupFailure
        PROCEDURE CODE                        id-S1Setup
        CRITICALITY                                reject
}


eNBConfigurationUpdate S1AP-ELEMENTARY-PROCEDURE ::= {
        INITIATING MESSAGE                S1AP-ENBConfigurationUpdate
        SUCCESSFUL OUTCOME                S1AP-ENBConfigurationUpdateAcknowledge
        UNSUCCESSFUL OUTCOME         S1AP-ENBConfigurationUpdateFailure
        PROCEDURE CODE                        id-ENBConfigurationUpdate
        CRITICALITY                                reject
}


mMEConfigurationUpdate S1AP-ELEMENTARY-PROCEDURE ::= {
        INITIATING MESSAGE                S1AP-MMEConfigurationUpdate
        SUCCESSFUL OUTCOME                S1AP-MMEConfigurationUpdateAcknowledge
        UNSUCCESSFUL OUTCOME         S1AP-MMEConfigurationUpdateFailure
        PROCEDURE CODE                        id-MMEConfigurationUpdate
        CRITICALITY                                reject
}


downlinkS1cdma2000tunneling S1AP-ELEMENTARY-PROCEDURE ::= {
        INITIATING MESSAGE                S1AP-DownlinkS1cdma2000tunneling
        PROCEDURE CODE                        id-DownlinkS1cdma2000tunneling
        CRITICALITY                                ignore
}


uplinkS1cdma2000tunneling S1AP-ELEMENTARY-PROCEDURE ::= {
        INITIATING MESSAGE                S1AP-UplinkS1cdma2000tunneling
        PROCEDURE CODE                        id-UplinkS1cdma2000tunneling
        CRITICALITY                                ignore
}


uEContextModification S1AP-ELEMENTARY-PROCEDURE ::= {
        INITIATING MESSAGE                S1AP-UEContextModificationRequest
        SUCCESSFUL OUTCOME                S1AP-UEContextModificationResponse
        UNSUCCESSFUL OUTCOME         S1AP-UEContextModificationFailure


        PROCEDURE CODE                id-UEContextModification
        CRITICALITY                reject
}


uECapabilityInfoIndication S1AP-ELEMENTARY-PROCEDURE ::= {
        INITIATING MESSAGE                S1AP-UECapabilityInfoIndication
        PROCEDURE CODE                        id-UECapabilityInfoIndication
        CRITICALITY                                ignore
}


uEContextRelease S1AP-ELEMENTARY-PROCEDURE ::= {
        INITIATING MESSAGE                S1AP-UEContextReleaseCommand
        SUCCESSFUL OUTCOME                S1AP-UEContextReleaseComplete
        PROCEDURE CODE                        id-UEContextRelease
        CRITICALITY                                reject
}


eNBStatusTransfer S1AP-ELEMENTARY-PROCEDURE ::= {
        INITIATING MESSAGE                S1AP-ENBStatusTransfer
        PROCEDURE CODE                        id-eNBStatusTransfer
        CRITICALITY                                ignore
}


mMEStatusTransfer S1AP-ELEMENTARY-PROCEDURE ::= {
        INITIATING MESSAGE                S1AP-MMEStatusTransfer
        PROCEDURE CODE                        id-MMEStatusTransfer
        CRITICALITY                                ignore
}


deactivateTrace S1AP-ELEMENTARY-PROCEDURE ::= {
        INITIATING MESSAGE                S1AP-DeactivateTrace
        PROCEDURE CODE                        id-DeactivateTrace
        CRITICALITY                                ignore
}


traceStart S1AP-ELEMENTARY-PROCEDURE ::= {
        INITIATING MESSAGE        S1AP-TraceStart
        PROCEDURE CODE                id-TraceStart
        CRITICALITY                        ignore
}


traceFailureIndication S1AP-ELEMENTARY-PROCEDURE ::= {
        INITIATING MESSAGE        S1AP-TraceFailureIndication
        PROCEDURE CODE                id-TraceFailureIndication
        CRITICALITY                        ignore
}
cellTrafficTrace S1AP-ELEMENTARY-PROCEDURE ::={
     INITIATING MESSAGE S1AP-CellTrafficTrace
     PROCEDURE CODE      id-CellTrafficTrace
     CRITICALITY         ignore
}


locationReportingControl S1AP-ELEMENTARY-PROCEDURE ::= {
        INITIATING MESSAGE                S1AP-LocationReportingControl
        PROCEDURE CODE                        id-LocationReportingControl
        CRITICALITY                                ignore
}


locationReportingFailureIndication S1AP-ELEMENTARY-PROCEDURE ::= {
        INITIATING MESSAGE                S1AP-LocationReportingFailureIndication
        PROCEDURE CODE                        id-LocationReportingFailureIndication
        CRITICALITY                                ignore
}


locationReport S1AP-ELEMENTARY-PROCEDURE ::= {
        INITIATING MESSAGE                S1AP-LocationReport
        PROCEDURE CODE                        id-LocationReport
        CRITICALITY                                ignore
}


overloadStart S1AP-ELEMENTARY-PROCEDURE ::= {
        INITIATING MESSAGE        S1AP-OverloadStart
        PROCEDURE CODE                id-OverloadStart
        CRITICALITY                ignore
}


overloadStop S1AP-ELEMENTARY-PROCEDURE ::= {
        INITIATING MESSAGE        S1AP-OverloadStop
        PROCEDURE CODE                id-OverloadStop
        CRITICALITY                reject
}


writeReplaceWarning S1AP-ELEMENTARY-PROCEDURE ::= {
        INITIATING MESSAGE        S1AP-WriteReplaceWarningRequest
        SUCCESSFUL OUTCOME        S1AP-WriteReplaceWarningResponse
        PROCEDURE CODE                id-WriteReplaceWarning
        CRITICALITY                        reject
}


eNBDirectInformationTransfer S1AP-ELEMENTARY-PROCEDURE ::= {
        INITIATING MESSAGE        S1AP-ENBDirectInformationTransfer
        PROCEDURE CODE                id-eNBDirectInformationTransfer
        CRITICALITY                        ignore
}


mMEDirectInformationTransfer S1AP-ELEMENTARY-PROCEDURE ::= {
        INITIATING MESSAGE        S1AP-MMEDirectInformationTransfer
        PROCEDURE CODE                id-MMEDirectInformationTransfer
        CRITICALITY                        ignore
}


eNBConfigurationTransfer S1AP-ELEMENTARY-PROCEDURE ::= {
        INITIATING MESSAGE                S1AP-ENBConfigurationTransfer
        PROCEDURE CODE                        id-eNBConfigurationTransfer
        CRITICALITY                                ignore
}


mMEConfigurationTransfer S1AP-ELEMENTARY-PROCEDURE ::= {
        INITIATING MESSAGE                S1AP-MMEConfigurationTransfer
        PROCEDURE CODE                        id-MMEConfigurationTransfer
        CRITICALITY                                ignore
}




privateMessage S1AP-ELEMENTARY-PROCEDURE ::= {
        INITIATING MESSAGE        S1AP-PrivateMessage
        PROCEDURE CODE                id-PrivateMessage
        CRITICALITY                        ignore
}


kill S1AP-ELEMENTARY-PROCEDURE ::= {
        INITIATING MESSAGE        S1AP-KillRequest
        SUCCESSFUL OUTCOME        S1AP-KillResponse
        PROCEDURE CODE                id-Kill
        CRITICALITY                        reject
}


downlinkUEAssociatedLPPaTransport S1AP-ELEMENTARY-PROCEDURE ::= {
        INITIATING MESSAGE                S1AP-DownlinkUEAssociatedLPPaTransport
        PROCEDURE CODE                        id-downlinkUEAssociatedLPPaTransport
        CRITICALITY                                ignore
}


uplinkUEAssociatedLPPaTransport S1AP-ELEMENTARY-PROCEDURE ::= {
        INITIATING MESSAGE                S1AP-UplinkUEAssociatedLPPaTransport
        PROCEDURE CODE                        id-uplinkUEAssociatedLPPaTransport
        CRITICALITY                                ignore
}
downlinkNonUEAssociatedLPPaTransport S1AP-ELEMENTARY-PROCEDURE ::= {
        INITIATING MESSAGE                S1AP-DownlinkNonUEAssociatedLPPaTransport
        PROCEDURE CODE                        id-downlinkNonUEAssociatedLPPaTransport
        CRITICALITY                                ignore
}


uplinkNonUEAssociatedLPPaTransport S1AP-ELEMENTARY-PROCEDURE ::= {
        INITIATING MESSAGE                S1AP-UplinkNonUEAssociatedLPPaTransport
        PROCEDURE CODE                        id-uplinkNonUEAssociatedLPPaTransport
        CRITICALITY                                ignore
}


END




-- **************************************************************
--
-- PDU definitions for S1AP.
--
-- **************************************************************


S1AP-PDU-Contents { 
itu-t (0) identified-organization (4) etsi (0) mobileDomain (0) 
eps-Access (21) modules (3) s1ap (1) version1 (1) s1ap-PDU-Contents (1) }


DEFINITIONS AUTOMATIC TAGS ::= 


BEGIN


-- **************************************************************
--
-- IE parameter types from other modules.
--
-- **************************************************************


IMPORTS
        S1AP-Criticality,
        S1AP-Presence,
        S1AP-ProcedureCode
FROM S1AP-CommonDataTypes
        
        S1AP-UEAggregateMaximumBitrate,
        S1AP-Cause,
        S1AP-CellAccessMode,
        S1AP-Cdma2000HORequiredIndication,
        S1AP-Cdma2000HOStatus,
        S1AP-Cdma2000OneXSRVCCInfo,
        S1AP-Cdma2000OneXRAND,
        S1AP-Cdma2000PDU,
        S1AP-Cdma2000RATType,
        S1AP-Cdma2000SectorID,
        S1AP-EUTRANRoundTripDelayEstimationInfo,
        S1AP-CNDomain,
        S1AP-ConcurrentWarningMessageIndicator,
        S1AP-CriticalityDiagnostics,
        S1AP-CSFallbackIndicator,
        S1AP-CSG-Id,
        S1AP-CSG-IdList, 
        S1AP-CSGMembershipStatus,
        S1AP-Data-Forwarding-Not-Possible,
        S1AP-Direct-Forwarding-Path-Availability,
        S1AP-Global-ENB-ID,
        S1AP-EUTRAN-CGI,
        S1AP-ENBname,
        S1AP-ENB-StatusTransfer-TransparentContainer,
        S1AP-ENB-UE-S1AP-ID,
        S1AP-ExtendedRepetitionPeriod,
        S1AP-GTP-TEID,
        S1AP-GUMMEI,
        S1AP-GUMMEIType,
        S1AP-HandoverRestrictionList,
        S1AP-HandoverType,
        S1AP-LAI,
        S1AP-LPPa-PDU,
        S1AP-ManagementBasedMDTAllowed,
        S1AP-MMEname,
        S1AP-MMERelaySupportIndicator,
        S1AP-MME-UE-S1AP-ID,
        S1AP-MSClassmark2,
        S1AP-MSClassmark3,
        S1AP-NAS-PDU,
        S1AP-NASSecurityParametersfromE-UTRAN,
        S1AP-NASSecurityParameterstoE-UTRAN,
        S1AP-OverloadResponse,
        S1AP-PagingDRX,
        S1AP-PagingPriority,
        S1AP-PLMNidentity,
        S1AP-RIMTransfer,
        S1AP-RelativeMMECapacity,
        S1AP-RequestType,
        S1AP-E-RAB-ID,
        S1AP-E-RABLevelQoSParameters,
        S1AP-E-RABList,
        S1AP-RelayNode-Indicator,
        S1AP-Routing-ID,
        S1AP-SecurityKey,
        S1AP-SecurityContext,
        S1AP-ServedGUMMEIs,
        S1AP-SONConfigurationTransfer,
        S1AP-Source-ToTarget-TransparentContainer,
        S1AP-SourceBSS-ToTargetBSS-TransparentContainer,
        S1AP-SourceeNB-ToTargeteNB-TransparentContainer,
        S1AP-SourceRNC-ToTargetRNC-TransparentContainer,
        S1AP-SubscriberProfileIDforRFP,
        S1AP-SRVCCOperationPossible,
        S1AP-SRVCCHOIndication,
        S1AP-SupportedTAs,
        S1AP-TAI,
        S1AP-Target-ToSource-TransparentContainer,
        S1AP-TargetBSS-ToSourceBSS-TransparentContainer,        
        S1AP-TargeteNB-ToSourceeNB-TransparentContainer,
        S1AP-TargetID,
        S1AP-TargetRNC-ToSourceRNC-TransparentContainer,
        S1AP-TimeToWait,
        S1AP-TraceActivation,
        S1AP-TrafficLoadReductionIndication,
        S1AP-E-UTRAN-Trace-ID,
        S1AP-TransportLayerAddress,
        S1AP-UEIdentityIndexValue,
        S1AP-UEPagingID,
        S1AP-UERadioCapability,
        S1AP-UE-S1AP-IDs,
        S1AP-UE-associatedLogicalS1-ConnectionItem,
        S1AP-UESecurityCapabilities,
        S1AP-S-TMSI,
        S1AP-MessageIdentifier,
        S1AP-SerialNumber,
        S1AP-WarningAreaList,
        S1AP-RepetitionPeriod,
        S1AP-NumberofBroadcastRequest,
        S1AP-WarningType,
        S1AP-WarningSecurityInfo,
        S1AP-DataCodingScheme,
        S1AP-WarningMessageContents,
        S1AP-BroadcastCompletedAreaList,
        S1AP-RRC-Establishment-Cause,
        S1AP-BroadcastCancelledAreaList,
        S1AP-PS-ServiceNotAvailable,
        S1AP-GUMMEIList,
        S1AP-Correlation-ID,
        S1AP-GWContextReleaseIndication,
        S1AP-PrivacyIndicator






FROM S1AP-IEs


        PrivateIE-Container{},
        ProtocolExtensionContainer{},
        ProtocolIE-Container{},
        ProtocolIE-ContainerList{},
        ProtocolIE-ContainerPair{},
        ProtocolIE-ContainerPairList{},
        ProtocolIE-SingleContainer{},
        S1AP-PRIVATE-IES,
        S1AP-PROTOCOL-EXTENSION,
        S1AP-PROTOCOL-IES,
        S1AP-PROTOCOL-IES-PAIR
FROM S1AP-Containers




        id-uEaggregateMaximumBitrate,
        id-Cause,
        id-CellAccessMode,
        id-cdma2000HORequiredIndication,
        id-cdma2000HOStatus,
        id-cdma2000OneXSRVCCInfo,
        id-cdma2000OneXRAND,
        id-cdma2000PDU,
        id-cdma2000RATType,
        id-cdma2000SectorID,
        id-EUTRANRoundTripDelayEstimationInfo,
        id-CNDomain,
        id-ConcurrentWarningMessageIndicator,
        id-CriticalityDiagnostics,
        id-CSFallbackIndicator,
        id-CSG-Id,
        id-CSG-IdList, 
        id-CSGMembershipStatus, 
        id-Data-Forwarding-Not-Possible,
        id-DefaultPagingDRX,
        id-Direct-Forwarding-Path-Availability,
        id-Global-ENB-ID,
        id-EUTRAN-CGI,
        id-eNBname,
        id-eNB-StatusTransfer-TransparentContainer,
        id-eNB-UE-S1AP-ID, 
        id-GERANtoLTEHOInformationRes,
        id-GUMMEI-ID,
        id-GUMMEIType,
        id-HandoverRestrictionList,
        id-HandoverType,
        id-InitialContextSetup,
        id-Inter-SystemInformationTransferTypeEDT,
        id-Inter-SystemInformationTransferTypeMDT,
        id-LPPa-PDU,
        id-NAS-DownlinkCount,
        id-ManagementBasedMDTAllowed,
        id-MMEname,
        id-MME-UE-S1AP-ID,
        id-MSClassmark2,
        id-MSClassmark3,
        id-NAS-PDU,
        id-NASSecurityParametersfromE-UTRAN,
        id-NASSecurityParameterstoE-UTRAN,
        id-OverloadResponse,
        id-pagingDRX,
        id-PagingPriority,
        id-RelativeMMECapacity,
        id-RequestType,
        id-Routing-ID,
        id-E-RABAdmittedItem,
        id-E-RABAdmittedList,
        id-E-RABDataForwardingItem,
        id-E-RABFailedToModifyList,
        id-E-RABFailedToReleaseList,
        id-E-RABFailedtoSetupItemHOReqAck,
        id-E-RABFailedToSetupListBearerSURes,
        id-E-RABFailedToSetupListCtxtSURes,
        id-E-RABFailedToSetupListHOReqAck,
        id-E-RABFailedToBeReleasedList,
        id-E-RABModify,
        id-E-RABModifyItemBearerModRes,
        id-E-RABModifyListBearerModRes,
        id-E-RABRelease,
        id-E-RABReleaseItemBearerRelComp,
        id-E-RABReleaseItemHOCmd,
        id-E-RABReleaseListBearerRelComp,
        id-E-RABReleaseIndication,
        id-E-RABSetup,
        id-E-RABSetupItemBearerSURes,
        id-E-RABSetupItemCtxtSURes,
        id-E-RABSetupListBearerSURes,
        id-E-RABSetupListCtxtSURes,
        id-E-RABSubjecttoDataForwardingList,
        id-E-RABToBeModifiedItemBearerModReq,
        id-E-RABToBeModifiedListBearerModReq,
        id-E-RABToBeReleasedList,
        id-E-RABReleasedList,
        id-E-RABToBeSetupItemBearerSUReq,
        id-E-RABToBeSetupItemCtxtSUReq,
        id-E-RABToBeSetupItemHOReq,
        id-E-RABToBeSetupListBearerSUReq,
        id-E-RABToBeSetupListCtxtSUReq,
        id-E-RABToBeSetupListHOReq,
        id-E-RABToBeSwitchedDLItem,
        id-E-RABToBeSwitchedDLList,
        id-E-RABToBeSwitchedULList,
        id-E-RABToBeSwitchedULItem,
        id-E-RABtoReleaseListHOCmd,
        id-SecurityKey,
        id-SecurityContext,
        id-ServedGUMMEIs,
        id-SONConfigurationTransferECT,
        id-SONConfigurationTransferMCT,
        id-Source-ToTarget-TransparentContainer,
        id-Source-ToTarget-TransparentContainer-Secondary,
        id-SourceMME-UE-S1AP-ID,
        id-SRVCCOperationPossible,
        id-SRVCCHOIndication,
        id-SubscriberProfileIDforRFP,
        id-SupportedTAs,
        id-S-TMSI,
        id-TAI,
        id-TAIItem,
        id-TAIList,
        id-Target-ToSource-TransparentContainer,
        id-Target-ToSource-TransparentContainer-Secondary,
        id-TargetID,
        id-TimeToWait,
        id-TraceActivation,
        id-TrafficLoadReductionIndication,
        id-E-UTRAN-Trace-ID,
        id-UEIdentityIndexValue,
        id-UEPagingID,
        id-UERadioCapability,
        id-UTRANtoLTEHOInformationRes,
        id-UE-associatedLogicalS1-ConnectionListResAck,
        id-UE-associatedLogicalS1-ConnectionItem,
        id-UESecurityCapabilities,
        id-UE-S1AP-IDs,
        id-ResetType,
        id-MessageIdentifier,
        id-SerialNumber,
        id-WarningAreaList,
        id-RepetitionPeriod,
        id-NumberofBroadcastRequest,
        id-WarningType,
        id-WarningSecurityInfo,
        id-DataCodingScheme,
        id-WarningMessageContents,
        id-BroadcastCompletedAreaList,
        id-BroadcastCancelledAreaList,
        id-RRC-Establishment-Cause,
        id-TraceCollectionEntityIPAddress,
        s1ap-maxnoofTAIs,
        s1ap-maxNrOfErrors,
        s1ap-maxNrOfE-RABs,
        s1ap-maxNrOfIndividualS1ConnectionsToReset,
        s1ap-maxnoofEmergencyAreaID,
        s1ap-maxnoofCellID,
        s1ap-maxnoofTAIforWarning,
        s1ap-maxnoofCellinTAI,
        s1ap-maxnoofCellinEAI,
        id-ExtendedRepetitionPeriod,
        id-PS-ServiceNotAvailable,
        id-RegisteredLAI,
        id-GUMMEIList,
        id-SourceMME-GUMMEI,
        id-MME-UE-S1AP-ID-2,
        id-GW-TransportLayerAddress,
        id-RelayNode-Indicator,
        id-Correlation-ID,
        id-MMERelaySupportIndicator,
        id-GWContextReleaseIndication,
        id-PrivacyIndicator,
        s1ap-maxProtocolIEs

FROM S1AP-Constants

        S1ap-IE

FROM S1AP-PDU;


-- **************************************************************
--
-- Common Container Lists
--
-- **************************************************************


E-RAB-IE-ContainerList                        { S1AP-PROTOCOL-IES      : IEsSetParam }        ::= ProtocolIE-ContainerList     { 1, s1ap-maxNrOfE-RABs,   {IEsSetParam} }
E-RAB-IE-ContainerPairList                { S1AP-PROTOCOL-IES-PAIR : IEsSetParam }        ::= ProtocolIE-ContainerPairList { 1, s1ap-maxNrOfE-RABs,   {IEsSetParam} }
ProtocolError-IE-ContainerList        { S1AP-PROTOCOL-IES      : IEsSetParam }        ::= ProtocolIE-ContainerList     { 1, s1ap-maxNrOfE-RABs,   {IEsSetParam} }


-- **************************************************************
--
-- HANDOVER PREPARATION ELEMENTARY PROCEDURE
--
-- **************************************************************


-- **************************************************************
--
-- Handover Required
--
-- **************************************************************


S1AP-HandoverRequired ::= SEQUENCE {
        protocolIEs                        ProtocolIE-Container       { { S1AP-HandoverRequiredIEs} },
        ...
}


S1AP-HandoverRequiredIEs S1AP-PROTOCOL-IES ::= {        
        { ID id-MME-UE-S1AP-ID                                                        CRITICALITY reject        TYPE S1AP-MME-UE-S1AP-ID                                                                         PRESENCE mandatory }|
        { ID id-eNB-UE-S1AP-ID                                                        CRITICALITY reject        TYPE S1AP-ENB-UE-S1AP-ID                                                                         PRESENCE mandatory }|
        { ID id-HandoverType                                                        CRITICALITY reject        TYPE S1AP-HandoverType                                                                         PRESENCE mandatory }|
        { ID id-Cause                                                                        CRITICALITY ignore        TYPE S1AP-Cause                                                                                         PRESENCE mandatory }|
        { ID id-TargetID                                                                CRITICALITY reject        TYPE S1AP-TargetID                                                                                 PRESENCE mandatory }|
        { ID id-Direct-Forwarding-Path-Availability                CRITICALITY ignore        TYPE S1AP-Direct-Forwarding-Path-Availability                PRESENCE optional }|
        { ID id-SRVCCHOIndication                                                CRITICALITY reject        TYPE S1AP-SRVCCHOIndication                                                                PRESENCE optional }|
        { ID id-Source-ToTarget-TransparentContainer        CRITICALITY reject        TYPE S1AP-Source-ToTarget-TransparentContainer         PRESENCE mandatory }|
        { ID id-Source-ToTarget-TransparentContainer-Secondary         CRITICALITY reject         TYPE S1AP-Source-ToTarget-TransparentContainer        PRESENCE optional }|
        { ID id-MSClassmark2                                                        CRITICALITY reject        TYPE S1AP-MSClassmark2                                                                        PRESENCE conditional }|
        { ID id-MSClassmark3                                                        CRITICALITY ignore        TYPE S1AP-MSClassmark3                                                                        PRESENCE conditional }|
        { ID id-CSG-Id                                                                        CRITICALITY reject        TYPE S1AP-CSG-Id                                                                                        PRESENCE optional }|
        { ID id-CellAccessMode                                                        CRITICALITY reject        TYPE S1AP-CellAccessMode                                                                        PRESENCE optional }|
        { ID id-PS-ServiceNotAvailable                                        CRITICALITY ignore        TYPE S1AP-PS-ServiceNotAvailable                                                PRESENCE optional },
        ...
}




-- **************************************************************
--
-- Handover Command
--
-- **************************************************************


S1AP-HandoverCommand ::= SEQUENCE {
        protocolIEs                        ProtocolIE-Container { { S1AP-HandoverCommandIEs} },
        ...
}


S1AP-HandoverCommandIEs S1AP-PROTOCOL-IES ::= {        
        { ID id-MME-UE-S1AP-ID                                                        CRITICALITY reject        TYPE S1AP-MME-UE-S1AP-ID                                                                                         PRESENCE mandatory        } |
        { ID id-eNB-UE-S1AP-ID                                                        CRITICALITY reject        TYPE S1AP-ENB-UE-S1AP-ID                                                                                         PRESENCE mandatory        } |
        { ID id-HandoverType                                                        CRITICALITY reject        TYPE S1AP-HandoverType                                                                                         PRESENCE mandatory        } |
        { ID id-NASSecurityParametersfromE-UTRAN                CRITICALITY reject        TYPE S1AP-NASSecurityParametersfromE-UTRAN                                        PRESENCE conditional
        -- This IE shall be present if S1AP-HandoverType IE is set to value "LTEtoUTRAN" or "LTEtoGERAN" --                        }|
        { ID id-E-RABSubjecttoDataForwardingList                CRITICALITY ignore        TYPE S1AP-E-RABSubjecttoDataForwardingList                                         PRESENCE optional        } |
        { ID id-E-RABtoReleaseListHOCmd                                        CRITICALITY ignore        TYPE S1AP-E-RABList                                                                                                 PRESENCE optional        } |
        { ID id-Target-ToSource-TransparentContainer        CRITICALITY        reject        TYPE S1AP-Target-ToSource-TransparentContainer                        PRESENCE mandatory }|
        { ID id-Target-ToSource-TransparentContainer-Secondary        CRITICALITY        reject        TYPE S1AP-Target-ToSource-TransparentContainer                        PRESENCE optional }|
        { ID id-CriticalityDiagnostics                                        CRITICALITY ignore        TYPE S1AP-CriticalityDiagnostics                                                                PRESENCE optional        },
        ...
}


S1AP-E-RABSubjecttoDataForwardingList ::= E-RAB-IE-ContainerList { {S1AP-E-RABDataForwardingItemIEs} }


S1AP-E-RABDataForwardingItemIEs S1AP-PROTOCOL-IES ::= {
        { ID id-E-RABDataForwardingItem                        CRITICALITY ignore        TYPE S1AP-E-RABDataForwardingItem                        PRESENCE mandatory        },
        ...
}


S1AP-E-RABDataForwardingItem ::= SEQUENCE {
        e-RAB-ID                                                        S1AP-E-RAB-ID,
        dL-transportLayerAddress                        S1AP-TransportLayerAddress                                                                                                         OPTIONAL,
        dL-gTP-TEID                                                        S1AP-GTP-TEID                                                                                                                                 OPTIONAL,
        uL-S1AP-TransportLayerAddress                        S1AP-TransportLayerAddress                                                                                                        OPTIONAL,
        uL-S1AP-GTP-TEID                                                        S1AP-GTP-TEID                                                                                                                                OPTIONAL,
        iE-Extensions                                                ProtocolExtensionContainer { { S1AP-E-RABDataForwardingItem-ExtIEs} }        OPTIONAL,
        ...
}


S1AP-E-RABDataForwardingItem-ExtIEs S1AP-PROTOCOL-EXTENSION ::= {
        ...
}






-- **************************************************************
--
-- Handover Preparation Failure
--
-- **************************************************************


S1AP-HandoverPreparationFailure ::= SEQUENCE {
        protocolIEs                        ProtocolIE-Container       { { S1AP-HandoverPreparationFailureIEs} },
        ...
}


S1AP-HandoverPreparationFailureIEs S1AP-PROTOCOL-IES ::= {        
        { ID id-MME-UE-S1AP-ID                                        CRITICALITY ignore        TYPE S1AP-MME-UE-S1AP-ID                                         PRESENCE mandatory        } |
        { ID id-eNB-UE-S1AP-ID                                        CRITICALITY ignore        TYPE S1AP-ENB-UE-S1AP-ID                                         PRESENCE mandatory        } |
        { ID id-Cause                                                        CRITICALITY ignore        TYPE S1AP-Cause                                                         PRESENCE mandatory        }|
        { ID id-CriticalityDiagnostics                        CRITICALITY ignore        TYPE S1AP-CriticalityDiagnostics                        PRESENCE optional        },
        ...
}


-- **************************************************************
--
-- HANDOVER RESOURCE ALLOCATION ELEMENTARY PROCEDURE
--
-- **************************************************************


-- **************************************************************
--
-- Handover Request
--
-- **************************************************************


S1AP-HandoverRequest ::= SEQUENCE {
        protocolIEs                        ProtocolIE-Container       { {S1AP-HandoverRequestIEs} },
        ...
}


S1AP-HandoverRequestIEs S1AP-PROTOCOL-IES ::= {        
        { ID id-MME-UE-S1AP-ID                                                        CRITICALITY reject        TYPE S1AP-MME-UE-S1AP-ID                                                PRESENCE mandatory}|
        { ID id-HandoverType                                                        CRITICALITY reject        TYPE S1AP-HandoverType                                                PRESENCE mandatory}|
        { ID id-Cause                                                                        CRITICALITY ignore        TYPE S1AP-Cause                                                                 PRESENCE mandatory}|
        { ID id-uEaggregateMaximumBitrate                                CRITICALITY reject        TYPE S1AP-UEAggregateMaximumBitrate                        PRESENCE mandatory}|
        { ID id-E-RABToBeSetupListHOReq                                        CRITICALITY reject        TYPE S1AP-E-RABToBeSetupListHOReq                        PRESENCE mandatory}|
        { ID id-Source-ToTarget-TransparentContainer        CRITICALITY reject        TYPE S1AP-Source-ToTarget-TransparentContainer        PRESENCE mandatory}|
        { ID id-UESecurityCapabilities                                        CRITICALITY reject        TYPE S1AP-UESecurityCapabilities                        PRESENCE mandatory}|
        { ID id-HandoverRestrictionList                                        CRITICALITY ignore        TYPE S1AP-HandoverRestrictionList                        PRESENCE optional}|
        { ID id-TraceActivation                                                        CRITICALITY ignore        TYPE S1AP-TraceActivation                                        PRESENCE optional}|
        { ID id-RequestType                                                                CRITICALITY ignore        TYPE S1AP-RequestType                                                PRESENCE optional}|
        { ID id-SRVCCOperationPossible                                        CRITICALITY ignore        TYPE S1AP-SRVCCOperationPossible                        PRESENCE optional}|
        { ID id-SecurityContext                                                        CRITICALITY reject        TYPE S1AP-SecurityContext                                        PRESENCE mandatory}|
        { ID id-NASSecurityParameterstoE-UTRAN                        CRITICALITY reject        TYPE S1AP-NASSecurityParameterstoE-UTRAN                PRESENCE conditional
        -- This IE shall be present if the Handover Type IE is set to the value "UTRANtoLTE" or "GERANtoLTE" --}|
        { ID id-CSG-Id                                                                        CRITICALITY reject        TYPE S1AP-CSG-Id                                                                PRESENCE optional}|
        { ID id-CSGMembershipStatus                                                CRITICALITY ignore        TYPE S1AP-CSGMembershipStatus                                PRESENCE optional}|
        { ID id-GUMMEI-ID                                                                CRITICALITY ignore        TYPE S1AP-GUMMEI                                                                PRESENCE optional}|
        { ID id-MME-UE-S1AP-ID-2                                                CRITICALITY ignore        TYPE S1AP-MME-UE-S1AP-ID                                                PRESENCE optional}|
        { ID id-ManagementBasedMDTAllowed                                CRITICALITY ignore        TYPE S1AP-ManagementBasedMDTAllowed                        PRESENCE optional},
        ...
}


S1AP-E-RABToBeSetupListHOReq                                         ::= E-RAB-IE-ContainerList { {S1AP-E-RABToBeSetupItemHOReqIEs} }


S1AP-E-RABToBeSetupItemHOReqIEs S1AP-PROTOCOL-IES ::= {
        { ID id-E-RABToBeSetupItemHOReq                        CRITICALITY reject        TYPE S1AP-E-RABToBeSetupItemHOReq                        PRESENCE mandatory        },
        ...
}


S1AP-E-RABToBeSetupItemHOReq ::= SEQUENCE {
        e-RAB-ID                                                        S1AP-E-RAB-ID,
        transportLayerAddress                                S1AP-TransportLayerAddress,
        gTP-TEID                                                        S1AP-GTP-TEID,
        e-RABlevelQosParameters                                S1AP-E-RABLevelQoSParameters,
        iE-Extensions                                                ProtocolExtensionContainer { {S1AP-E-RABToBeSetupItemHOReq-ExtIEs} }                        OPTIONAL,
        ...
}


S1AP-E-RABToBeSetupItemHOReq-ExtIEs S1AP-PROTOCOL-EXTENSION ::= {
        {ID        id-Data-Forwarding-Not-Possible           CRITICALITY ignore        EXTENSION  S1AP-Data-Forwarding-Not-Possible   PRESENCE optional},
        ...
}


-- **************************************************************
--
-- Handover Request Acknowledge
--
-- **************************************************************


S1AP-HandoverRequestAcknowledge ::= SEQUENCE {
        protocolIEs                        ProtocolIE-Container       { {S1AP-HandoverRequestAcknowledgeIEs} },
        ...
}


S1AP-HandoverRequestAcknowledgeIEs S1AP-PROTOCOL-IES ::= {        
        { ID id-MME-UE-S1AP-ID                                                        CRITICALITY ignore        TYPE S1AP-MME-UE-S1AP-ID                                                                        PRESENCE mandatory        } |
        { ID id-eNB-UE-S1AP-ID                                                        CRITICALITY ignore        TYPE S1AP-ENB-UE-S1AP-ID                                                                        PRESENCE mandatory        } |
        { ID id-E-RABAdmittedList                                                CRITICALITY ignore        TYPE S1AP-E-RABAdmittedList                                                                PRESENCE mandatory        } |
        { ID id-E-RABFailedToSetupListHOReqAck                        CRITICALITY ignore        TYPE S1AP-E-RABFailedtoSetupListHOReqAck                        PRESENCE optional        } |
        { ID id-Target-ToSource-TransparentContainer        CRITICALITY reject        TYPE S1AP-Target-ToSource-TransparentContainer        PRESENCE mandatory }|
        { ID id-CSG-Id                                                                        CRITICALITY ignore        TYPE S1AP-CSG-Id                                                                                        PRESENCE optional } |
        { ID id-CriticalityDiagnostics                                        CRITICALITY ignore        TYPE S1AP-CriticalityDiagnostics                                                PRESENCE optional        },
        ...
}


S1AP-E-RABAdmittedList                                         ::= E-RAB-IE-ContainerList { {S1AP-E-RABAdmittedItemIEs} }


S1AP-E-RABAdmittedItemIEs S1AP-PROTOCOL-IES ::= {
        { ID id-E-RABAdmittedItem                        CRITICALITY ignore        TYPE S1AP-E-RABAdmittedItem                        PRESENCE mandatory        },
        ...
}


S1AP-E-RABAdmittedItem ::= SEQUENCE {
        e-RAB-ID                                                S1AP-E-RAB-ID,
        transportLayerAddress                        S1AP-TransportLayerAddress,
        gTP-TEID                                                S1AP-GTP-TEID,
        dL-transportLayerAddress                S1AP-TransportLayerAddress        OPTIONAL,
        dL-gTP-TEID                                                S1AP-GTP-TEID                                OPTIONAL,
        uL-S1AP-TransportLayerAddress                S1AP-TransportLayerAddress        OPTIONAL,
        uL-S1AP-GTP-TEID                                                S1AP-GTP-TEID                                OPTIONAL,
        iE-Extensions                                        ProtocolExtensionContainer { {S1AP-E-RABAdmittedItem-ExtIEs} }        OPTIONAL,
        ...
}


S1AP-E-RABAdmittedItem-ExtIEs S1AP-PROTOCOL-EXTENSION ::= {
        ...
}


S1AP-E-RABFailedtoSetupListHOReqAck                                         ::= E-RAB-IE-ContainerList { {S1AP-E-RABFailedtoSetupItemHOReqAckIEs} }


S1AP-E-RABFailedtoSetupItemHOReqAckIEs S1AP-PROTOCOL-IES ::= {
        { ID id-E-RABFailedtoSetupItemHOReqAck                        CRITICALITY ignore        TYPE S1AP-E-RABFailedToSetupItemHOReqAck                        PRESENCE mandatory        },
        ...
}


S1AP-E-RABFailedToSetupItemHOReqAck ::= SEQUENCE {
        e-RAB-ID                                                S1AP-E-RAB-ID,
        cause                                S1AP-Cause,
        iE-Extensions                                        ProtocolExtensionContainer { { S1AP-E-RABFailedToSetupItemHOReqAckExtIEs} }                        OPTIONAL,
        ...
}


S1AP-E-RABFailedToSetupItemHOReqAckExtIEs S1AP-PROTOCOL-EXTENSION ::= {
        ...
}




-- **************************************************************
--
-- Handover Failure
--
-- **************************************************************


S1AP-HandoverFailure ::= SEQUENCE {
        protocolIEs                        ProtocolIE-Container       { { S1AP-HandoverFailureIEs} },
        ...
}


S1AP-HandoverFailureIEs S1AP-PROTOCOL-IES ::= {        
        { ID id-MME-UE-S1AP-ID                                CRITICALITY ignore        TYPE S1AP-MME-UE-S1AP-ID                                PRESENCE mandatory        } |
        { ID id-Cause                                                CRITICALITY ignore        TYPE S1AP-Cause                                                 PRESENCE mandatory        }|
        { ID id-CriticalityDiagnostics                CRITICALITY ignore        TYPE S1AP-CriticalityDiagnostics                PRESENCE optional        },
        ...
}


-- **************************************************************
--
-- HANDOVER NOTIFICATION ELEMENTARY PROCEDURE
--
-- **************************************************************


-- **************************************************************
--
-- Handover Notify
--
-- **************************************************************


S1AP-HandoverNotify ::= SEQUENCE {
        protocolIEs                        ProtocolIE-Container       { { S1AP-HandoverNotifyIEs} },
        ...
}


S1AP-HandoverNotifyIEs S1AP-PROTOCOL-IES ::= {        
        { ID id-MME-UE-S1AP-ID                        CRITICALITY reject        TYPE S1AP-MME-UE-S1AP-ID                        PRESENCE mandatory        } |
        { ID id-eNB-UE-S1AP-ID                        CRITICALITY reject        TYPE S1AP-ENB-UE-S1AP-ID                        PRESENCE mandatory        } |
        { ID id-EUTRAN-CGI                                CRITICALITY ignore        TYPE S1AP-EUTRAN-CGI                                PRESENCE mandatory}|
        { ID id-TAI                                                CRITICALITY ignore        TYPE S1AP-TAI                                        PRESENCE mandatory},
        ...
}


-- **************************************************************
--
-- PATH SWITCH REQUEST ELEMENTARY PROCEDURE
--
-- **************************************************************


-- **************************************************************
--
-- Path Switch Request
--
-- **************************************************************


S1AP-PathSwitchRequest ::= SEQUENCE {
        protocolIEs                        ProtocolIE-Container       { { S1AP-PathSwitchRequestIEs} },
        ...
}


S1AP-PathSwitchRequestIEs S1AP-PROTOCOL-IES ::= {        
        { ID id-eNB-UE-S1AP-ID                                        CRITICALITY reject        TYPE S1AP-ENB-UE-S1AP-ID                                 PRESENCE mandatory}|
        { ID id-E-RABToBeSwitchedDLList                        CRITICALITY reject        TYPE S1AP-E-RABToBeSwitchedDLList        PRESENCE mandatory}|
        { ID id-SourceMME-UE-S1AP-ID                        CRITICALITY reject        TYPE S1AP-MME-UE-S1AP-ID                                 PRESENCE mandatory}|
        { ID id-EUTRAN-CGI                                                CRITICALITY ignore        TYPE S1AP-EUTRAN-CGI                                        PRESENCE mandatory}|
        { ID id-TAI                                                                CRITICALITY ignore        TYPE S1AP-TAI                                                PRESENCE mandatory}|
        { ID id-UESecurityCapabilities                        CRITICALITY ignore        TYPE S1AP-UESecurityCapabilities                PRESENCE mandatory}|
        { ID id-CSG-Id                                                        CRITICALITY ignore        TYPE S1AP-CSG-Id                                                PRESENCE optional}|
        { ID id-CellAccessMode                                        CRITICALITY ignore        TYPE S1AP-CellAccessMode                                PRESENCE optional}|
        { ID id-SourceMME-GUMMEI                                CRITICALITY ignore        TYPE S1AP-GUMMEI                                                PRESENCE optional},
        ...
}


S1AP-E-RABToBeSwitchedDLList                                         ::= E-RAB-IE-ContainerList { {S1AP-E-RABToBeSwitchedDLItemIEs} }


S1AP-E-RABToBeSwitchedDLItemIEs S1AP-PROTOCOL-IES ::= {
        { ID id-E-RABToBeSwitchedDLItem                        CRITICALITY reject        TYPE S1AP-E-RABToBeSwitchedDLItem                        PRESENCE mandatory        },
        ...
}


S1AP-E-RABToBeSwitchedDLItem ::= SEQUENCE {
        e-RAB-ID                                                S1AP-E-RAB-ID,
        transportLayerAddress                                S1AP-TransportLayerAddress,
        gTP-TEID                                        S1AP-GTP-TEID,
        iE-Extensions                                        ProtocolExtensionContainer { { S1AP-E-RABToBeSwitchedDLItem-ExtIEs} }                        OPTIONAL,
        ...
}


S1AP-E-RABToBeSwitchedDLItem-ExtIEs S1AP-PROTOCOL-EXTENSION ::= {
        ...
}


-- **************************************************************
--
-- Path Switch Request Acknowledge
--
-- **************************************************************


S1AP-PathSwitchRequestAcknowledge ::= SEQUENCE {
        protocolIEs                        ProtocolIE-Container       { { S1AP-PathSwitchRequestAcknowledgeIEs} },
        ...
}


S1AP-PathSwitchRequestAcknowledgeIEs S1AP-PROTOCOL-IES ::= {        
        { ID id-MME-UE-S1AP-ID                                        CRITICALITY ignore        TYPE S1AP-MME-UE-S1AP-ID                                        PRESENCE mandatory}|
        { ID id-eNB-UE-S1AP-ID                                        CRITICALITY ignore        TYPE S1AP-ENB-UE-S1AP-ID                                        PRESENCE mandatory}|
        { ID id-uEaggregateMaximumBitrate                CRITICALITY ignore        TYPE S1AP-UEAggregateMaximumBitrate                PRESENCE optional}|
        { ID id-E-RABToBeSwitchedULList                        CRITICALITY ignore        TYPE S1AP-E-RABToBeSwitchedULList                PRESENCE optional}|
        { ID id-E-RABToBeReleasedList                        CRITICALITY ignore        TYPE S1AP-E-RABList                                                PRESENCE optional}|
        { ID id-SecurityContext                                        CRITICALITY reject        TYPE S1AP-SecurityContext                                PRESENCE mandatory}|
        { ID id-CriticalityDiagnostics                        CRITICALITY ignore        TYPE S1AP-CriticalityDiagnostics                        PRESENCE optional}|
        { ID id-MME-UE-S1AP-ID-2                                CRITICALITY ignore        TYPE S1AP-MME-UE-S1AP-ID                                        PRESENCE optional},
        ...
}


S1AP-E-RABToBeSwitchedULList ::= E-RAB-IE-ContainerList { {S1AP-E-RABToBeSwitchedULItemIEs} }


S1AP-E-RABToBeSwitchedULItemIEs S1AP-PROTOCOL-IES ::= {
        { ID id-E-RABToBeSwitchedULItem                CRITICALITY ignore        TYPE S1AP-E-RABToBeSwitchedULItem        PRESENCE mandatory        },
        ...
}


S1AP-E-RABToBeSwitchedULItem ::= SEQUENCE {
        e-RAB-ID                                                        S1AP-E-RAB-ID,
        transportLayerAddress                                S1AP-TransportLayerAddress,
        gTP-TEID                                                        S1AP-GTP-TEID,
        iE-Extensions                                                ProtocolExtensionContainer { { S1AP-E-RABToBeSwitchedULItem-ExtIEs} }                        OPTIONAL,
        ...
}


S1AP-E-RABToBeSwitchedULItem-ExtIEs S1AP-PROTOCOL-EXTENSION ::= {
        ...
}




-- **************************************************************
--
-- Path Switch Request Failure
--
-- **************************************************************


S1AP-PathSwitchRequestFailure ::= SEQUENCE {
        protocolIEs                        ProtocolIE-Container       { { S1AP-PathSwitchRequestFailureIEs} },
        ...
}


S1AP-PathSwitchRequestFailureIEs S1AP-PROTOCOL-IES ::= {        
        { ID id-MME-UE-S1AP-ID                                        CRITICALITY ignore        TYPE S1AP-MME-UE-S1AP-ID                                         PRESENCE mandatory        } |
        { ID id-eNB-UE-S1AP-ID                                        CRITICALITY ignore        TYPE S1AP-ENB-UE-S1AP-ID                                         PRESENCE mandatory        } |
        { ID id-Cause                                                        CRITICALITY ignore        TYPE S1AP-Cause                                                         PRESENCE mandatory        }|
        { ID id-CriticalityDiagnostics                        CRITICALITY ignore        TYPE S1AP-CriticalityDiagnostics                        PRESENCE optional        },
        ...
}


-- **************************************************************
--
-- HANDOVER CANCEL ELEMENTARY PROCEDURE
--
-- **************************************************************


-- **************************************************************
--
-- Handover Cancel
--
-- **************************************************************


S1AP-HandoverCancel ::= SEQUENCE {
        protocolIEs                        ProtocolIE-Container       { { S1AP-HandoverCancelIEs} },
        ...
}


S1AP-HandoverCancelIEs S1AP-PROTOCOL-IES ::= {        
        { ID id-MME-UE-S1AP-ID                                        CRITICALITY reject        TYPE S1AP-MME-UE-S1AP-ID                                         PRESENCE mandatory        } |
        { ID id-eNB-UE-S1AP-ID                                        CRITICALITY reject        TYPE S1AP-ENB-UE-S1AP-ID                                         PRESENCE mandatory        } |
        { ID id-Cause                                        CRITICALITY ignore        TYPE S1AP-Cause                                         PRESENCE mandatory        },
        ...
}


-- **************************************************************
--
-- Handover Cancel Request Acknowledge
--
-- **************************************************************


S1AP-HandoverCancelAcknowledge ::= SEQUENCE {
        protocolIEs                        ProtocolIE-Container       { { S1AP-HandoverCancelAcknowledgeIEs} },
        ...
}


S1AP-HandoverCancelAcknowledgeIEs S1AP-PROTOCOL-IES ::= {        
        { ID id-MME-UE-S1AP-ID                                        CRITICALITY ignore        TYPE S1AP-MME-UE-S1AP-ID                                         PRESENCE mandatory        } |
        { ID id-eNB-UE-S1AP-ID                                        CRITICALITY ignore        TYPE S1AP-ENB-UE-S1AP-ID                                         PRESENCE mandatory        }|
        { ID id-CriticalityDiagnostics                CRITICALITY ignore        TYPE S1AP-CriticalityDiagnostics                        PRESENCE optional        },
        ...
}


-- **************************************************************
--
-- E-RAB SETUP ELEMENTARY PROCEDURE
--
-- **************************************************************


-- **************************************************************
--
-- E-RAB Setup Request
--
-- **************************************************************


S1AP-E-RABSetupRequest ::= SEQUENCE {
        protocolIEs                        ProtocolIE-Container       { {S1AP-E-RABSetupRequestIEs} },
        ...
}


S1AP-E-RABSetupRequestIEs S1AP-PROTOCOL-IES ::= {
        { ID id-MME-UE-S1AP-ID                                        CRITICALITY reject        TYPE S1AP-MME-UE-S1AP-ID                                                         PRESENCE mandatory        }|
        { ID id-eNB-UE-S1AP-ID                                        CRITICALITY reject        TYPE S1AP-ENB-UE-S1AP-ID                                                         PRESENCE mandatory        }|
        { ID id-uEaggregateMaximumBitrate                CRITICALITY reject        TYPE S1AP-UEAggregateMaximumBitrate                                PRESENCE optional        }|
        { ID id-E-RABToBeSetupListBearerSUReq        CRITICALITY reject        TYPE S1AP-E-RABToBeSetupListBearerSUReq                PRESENCE mandatory        },
        ...
}


S1AP-E-RABToBeSetupListBearerSUReq ::= SEQUENCE (SIZE(1.. s1ap-maxNrOfE-RABs)) OF ProtocolIE-SingleContainer { {S1AP-E-RABToBeSetupItemBearerSUReqIEs} }


S1AP-E-RABToBeSetupItemBearerSUReqIEs         S1AP-PROTOCOL-IES ::= {
        { ID id-E-RABToBeSetupItemBearerSUReq         CRITICALITY reject         TYPE S1AP-E-RABToBeSetupItemBearerSUReq         PRESENCE mandatory },
        ...
}


S1AP-E-RABToBeSetupItemBearerSUReq ::= SEQUENCE {
        e-RAB-ID                                                S1AP-E-RAB-ID,
        e-RABlevelQoSParameters                        S1AP-E-RABLevelQoSParameters,
        transportLayerAddress                         S1AP-TransportLayerAddress,
        gTP-TEID                                                S1AP-GTP-TEID,
        nAS-PDU                                                        S1AP-NAS-PDU,
        iE-Extensions                                        ProtocolExtensionContainer { {S1AP-E-RABToBeSetupItemBearerSUReqExtIEs} } OPTIONAL,
        ...
}




S1AP-E-RABToBeSetupItemBearerSUReqExtIEs S1AP-PROTOCOL-EXTENSION ::= {
        { ID id-Correlation-ID                CRITICALITY ignore        EXTENSION S1AP-Correlation-ID                PRESENCE optional},
        ...
}




-- **************************************************************
--
-- E-RAB Setup Response
--
-- **************************************************************


S1AP-E-RABSetupResponse ::= SEQUENCE {
        protocolIEs                        ProtocolIE-Container       { {S1AP-E-RABSetupResponseIEs} },
        ...
}


S1AP-E-RABSetupResponseIEs S1AP-PROTOCOL-IES ::= {
        { ID id-MME-UE-S1AP-ID                                CRITICALITY ignore        TYPE S1AP-MME-UE-S1AP-ID                                         PRESENCE mandatory        }|
        { ID id-eNB-UE-S1AP-ID                                CRITICALITY ignore        TYPE S1AP-ENB-UE-S1AP-ID                                         PRESENCE mandatory        }|
        { ID id-E-RABSetupListBearerSURes                                CRITICALITY ignore        TYPE S1AP-E-RABSetupListBearerSURes                        PRESENCE optional        }|
        { ID id-E-RABFailedToSetupListBearerSURes                CRITICALITY ignore        TYPE S1AP-E-RABList                                        PRESENCE optional        }|
        { ID id-CriticalityDiagnostics                CRITICALITY ignore        TYPE S1AP-CriticalityDiagnostics                        PRESENCE optional        },
        ...
}




S1AP-E-RABSetupListBearerSURes ::= SEQUENCE (SIZE(1.. s1ap-maxNrOfE-RABs)) OF ProtocolIE-SingleContainer { {S1AP-E-RABSetupItemBearerSUResIEs} }


S1AP-E-RABSetupItemBearerSUResIEs         S1AP-PROTOCOL-IES ::= {
        { ID id-E-RABSetupItemBearerSURes         CRITICALITY ignore         TYPE S1AP-E-RABSetupItemBearerSURes         PRESENCE mandatory },
        ...
}


S1AP-E-RABSetupItemBearerSURes ::= SEQUENCE {
        e-RAB-ID                                        S1AP-E-RAB-ID,
        transportLayerAddress                S1AP-TransportLayerAddress,
        gTP-TEID                                        S1AP-GTP-TEID,
        iE-Extensions                                ProtocolExtensionContainer { {S1AP-E-RABSetupItemBearerSUResExtIEs} } OPTIONAL,
        ...
}




S1AP-E-RABSetupItemBearerSUResExtIEs S1AP-PROTOCOL-EXTENSION ::= {
        ...
}






-- **************************************************************
--
-- E-RAB MODIFY ELEMENTARY PROCEDURE
--
-- **************************************************************


-- **************************************************************
--
-- E-RAB Modify Request
--
-- **************************************************************


S1AP-E-RABModifyRequest ::= SEQUENCE {
        protocolIEs                        ProtocolIE-Container       { {S1AP-E-RABModifyRequestIEs} },
        ...
}


S1AP-E-RABModifyRequestIEs S1AP-PROTOCOL-IES ::= {
        { ID id-MME-UE-S1AP-ID                                                CRITICALITY reject        TYPE S1AP-MME-UE-S1AP-ID                                                                PRESENCE mandatory        }|
        { ID id-eNB-UE-S1AP-ID                                                CRITICALITY reject        TYPE S1AP-ENB-UE-S1AP-ID                                                                PRESENCE mandatory        }|
        { ID id-uEaggregateMaximumBitrate                        CRITICALITY reject        TYPE S1AP-UEAggregateMaximumBitrate                                PRESENCE optional        }|
        { ID id-E-RABToBeModifiedListBearerModReq        CRITICALITY reject        TYPE S1AP-E-RABToBeModifiedListBearerModReq                PRESENCE mandatory        },
        ...
}


S1AP-E-RABToBeModifiedListBearerModReq ::= SEQUENCE (SIZE(1.. s1ap-maxNrOfE-RABs)) OF ProtocolIE-SingleContainer { {S1AP-E-RABToBeModifiedItemBearerModReqIEs} }


S1AP-E-RABToBeModifiedItemBearerModReqIEs         S1AP-PROTOCOL-IES ::= {
        { ID id-E-RABToBeModifiedItemBearerModReq         CRITICALITY reject         TYPE S1AP-E-RABToBeModifiedItemBearerModReq         PRESENCE mandatory },
        ...
}


S1AP-E-RABToBeModifiedItemBearerModReq ::= SEQUENCE {
        e-RAB-ID                                                S1AP-E-RAB-ID,
        e-RABLevelQoSParameters                        S1AP-E-RABLevelQoSParameters,
        nAS-PDU                                                        S1AP-NAS-PDU,
        iE-Extensions                                        ProtocolExtensionContainer { {S1AP-E-RABToBeModifyItemBearerModReqExtIEs} } OPTIONAL,
        ...
}




S1AP-E-RABToBeModifyItemBearerModReqExtIEs S1AP-PROTOCOL-EXTENSION ::= {
        ...
}






-- **************************************************************
--
-- E-RAB Modify Response
--
-- **************************************************************


S1AP-E-RABModifyResponse ::= SEQUENCE {
        protocolIEs                        ProtocolIE-Container       { {S1AP-E-RABModifyResponseIEs} },
        ...
}


S1AP-E-RABModifyResponseIEs S1AP-PROTOCOL-IES ::= {
        { ID id-MME-UE-S1AP-ID                                CRITICALITY ignore        TYPE S1AP-MME-UE-S1AP-ID                                         PRESENCE mandatory        }|
        { ID id-eNB-UE-S1AP-ID                                CRITICALITY ignore        TYPE S1AP-ENB-UE-S1AP-ID                                         PRESENCE mandatory        }|
        { ID id-E-RABModifyListBearerModRes                                CRITICALITY ignore        TYPE S1AP-E-RABModifyListBearerModRes                PRESENCE optional        }|
        { ID id-E-RABFailedToModifyList                CRITICALITY ignore        TYPE S1AP-E-RABList                                PRESENCE optional        }|
        { ID id-CriticalityDiagnostics                CRITICALITY ignore        TYPE S1AP-CriticalityDiagnostics                        PRESENCE optional        },
        ...
}




S1AP-E-RABModifyListBearerModRes ::= SEQUENCE (SIZE(1.. s1ap-maxNrOfE-RABs)) OF ProtocolIE-SingleContainer { {S1AP-E-RABModifyItemBearerModResIEs} }


S1AP-E-RABModifyItemBearerModResIEs         S1AP-PROTOCOL-IES ::= {
        { ID id-E-RABModifyItemBearerModRes         CRITICALITY ignore         TYPE S1AP-E-RABModifyItemBearerModRes         PRESENCE mandatory },
        ...
}


S1AP-E-RABModifyItemBearerModRes ::= SEQUENCE {
        e-RAB-ID                                        S1AP-E-RAB-ID,
        iE-Extensions                                        ProtocolExtensionContainer { {S1AP-E-RABModifyItemBearerModResExtIEs} } OPTIONAL,
        ...
}




S1AP-E-RABModifyItemBearerModResExtIEs S1AP-PROTOCOL-EXTENSION ::= {
        ...
}








-- **************************************************************
--
-- E-RAB RELEASE ELEMENTARY PROCEDURE
--
-- **************************************************************


-- **************************************************************
--
-- E-RAB Release Command
--
-- **************************************************************


S1AP-E-RABReleaseCommand ::= SEQUENCE {
        protocolIEs                        ProtocolIE-Container                { {S1AP-E-RABReleaseCommandIEs} },
        ...
}


S1AP-E-RABReleaseCommandIEs S1AP-PROTOCOL-IES ::= {
        { ID id-MME-UE-S1AP-ID                                CRITICALITY reject        TYPE S1AP-MME-UE-S1AP-ID                                         PRESENCE mandatory        }|
        { ID id-eNB-UE-S1AP-ID                                CRITICALITY reject        TYPE S1AP-ENB-UE-S1AP-ID                                         PRESENCE mandatory        }|
        { ID id-uEaggregateMaximumBitrate                CRITICALITY reject        TYPE S1AP-UEAggregateMaximumBitrate                PRESENCE optional        }|
        { ID id-E-RABToBeReleasedList                CRITICALITY ignore        TYPE S1AP-E-RABList                                        PRESENCE mandatory        }|
        { ID id-NAS-PDU                                                        CRITICALITY ignore        TYPE S1AP-NAS-PDU                                                PRESENCE optional        },
        ...
}




-- **************************************************************
--
-- E-RAB Release Response
--
-- **************************************************************


S1AP-E-RABReleaseResponse ::= SEQUENCE {
        protocolIEs                        ProtocolIE-Container       { { S1AP-E-RABReleaseResponseIEs } },
        ...
}


S1AP-E-RABReleaseResponseIEs S1AP-PROTOCOL-IES ::= {
        { ID id-MME-UE-S1AP-ID                                CRITICALITY ignore        TYPE S1AP-MME-UE-S1AP-ID                                         PRESENCE mandatory        }|
        { ID id-eNB-UE-S1AP-ID                                CRITICALITY ignore        TYPE S1AP-ENB-UE-S1AP-ID                                         PRESENCE mandatory        }|
        { ID id-E-RABReleaseListBearerRelComp                                CRITICALITY ignore        TYPE S1AP-E-RABReleaseListBearerRelComp                PRESENCE optional        }|
        { ID id-E-RABFailedToReleaseList                CRITICALITY ignore        TYPE S1AP-E-RABList                                PRESENCE optional        }|
        { ID id-CriticalityDiagnostics                CRITICALITY ignore        TYPE S1AP-CriticalityDiagnostics                        PRESENCE optional        },
        ...
}




S1AP-E-RABReleaseListBearerRelComp ::= SEQUENCE (SIZE(1.. s1ap-maxNrOfE-RABs)) OF ProtocolIE-SingleContainer { {S1AP-E-RABReleaseItemBearerRelCompIEs} }


S1AP-E-RABReleaseItemBearerRelCompIEs         S1AP-PROTOCOL-IES ::= {
        { ID id-E-RABReleaseItemBearerRelComp         CRITICALITY ignore         TYPE S1AP-E-RABReleaseItemBearerRelComp         PRESENCE mandatory },
        ...
}


S1AP-E-RABReleaseItemBearerRelComp ::= SEQUENCE {
        e-RAB-ID                                        S1AP-E-RAB-ID,
        iE-Extensions                                        ProtocolExtensionContainer { {S1AP-E-RABReleaseItemBearerRelCompExtIEs} } OPTIONAL,
        ...
}




S1AP-E-RABReleaseItemBearerRelCompExtIEs S1AP-PROTOCOL-EXTENSION ::= {
        ...
}






-- **************************************************************
--
-- E-RAB RELEASE INDICATION ELEMENTARY PROCEDURE
--
-- **************************************************************


-- **************************************************************
--
-- E-RAB Release Indication
--
-- **************************************************************


S1AP-E-RABReleaseIndication ::= SEQUENCE {
        protocolIEs                        ProtocolIE-Container       { {S1AP-E-RABReleaseIndicationIEs} },
        ...
}


S1AP-E-RABReleaseIndicationIEs S1AP-PROTOCOL-IES ::= {
        { ID id-MME-UE-S1AP-ID                                CRITICALITY reject        TYPE S1AP-MME-UE-S1AP-ID                                         PRESENCE mandatory        }|
        { ID id-eNB-UE-S1AP-ID                                CRITICALITY reject        TYPE S1AP-ENB-UE-S1AP-ID                                         PRESENCE mandatory        }|
        { ID id-E-RABReleasedList                        CRITICALITY ignore        TYPE S1AP-E-RABList                                        PRESENCE mandatory        },
        ...
}
-- **************************************************************
--
-- INITIAL CONTEXT SETUP ELEMENTARY PROCEDURE
--
-- **************************************************************


-- **************************************************************
--
-- Initial Context Setup Request
--
-- **************************************************************


S1AP-InitialContextSetupRequest ::= SEQUENCE {
        protocolIEs                        ProtocolIE-Container       { {S1AP-InitialContextSetupRequestIEs} },
        ...
}


S1AP-InitialContextSetupRequestIEs S1AP-PROTOCOL-IES ::= {
        { ID id-MME-UE-S1AP-ID                                CRITICALITY reject        TYPE S1AP-MME-UE-S1AP-ID                                         PRESENCE mandatory}|
        { ID id-eNB-UE-S1AP-ID                                CRITICALITY reject        TYPE S1AP-ENB-UE-S1AP-ID                                         PRESENCE mandatory}|
        { ID id-uEaggregateMaximumBitrate        CRITICALITY reject        TYPE S1AP-UEAggregateMaximumBitrate                PRESENCE mandatory}|
        { ID id-E-RABToBeSetupListCtxtSUReq        CRITICALITY reject        TYPE S1AP-E-RABToBeSetupListCtxtSUReq        PRESENCE mandatory}|
        { ID id-UESecurityCapabilities                CRITICALITY reject        TYPE S1AP-UESecurityCapabilities                        PRESENCE mandatory}|
        { ID id-SecurityKey                                        CRITICALITY reject        TYPE S1AP-SecurityKey                                        PRESENCE mandatory}|
        { ID id-TraceActivation                                CRITICALITY ignore        TYPE S1AP-TraceActivation                                 PRESENCE optional}|
        { ID id-HandoverRestrictionList                CRITICALITY ignore        TYPE S1AP-HandoverRestrictionList                PRESENCE optional}|
        { ID id-UERadioCapability                        CRITICALITY ignore        TYPE S1AP-UERadioCapability                                PRESENCE optional}|
        { ID id-SubscriberProfileIDforRFP        CRITICALITY ignore        TYPE S1AP-SubscriberProfileIDforRFP                PRESENCE optional}|
        { ID id-CSFallbackIndicator                        CRITICALITY reject        TYPE S1AP-CSFallbackIndicator                        PRESENCE optional}|
        { ID id-SRVCCOperationPossible                CRITICALITY ignore        TYPE S1AP-SRVCCOperationPossible                        PRESENCE optional}|
        { ID id-CSGMembershipStatus                        CRITICALITY ignore        TYPE S1AP-CSGMembershipStatus                        PRESENCE optional}|
        { ID id-RegisteredLAI                                CRITICALITY ignore        TYPE S1AP-LAI                                                        PRESENCE optional}|
        { ID id-GUMMEI-ID                                        CRITICALITY ignore        TYPE S1AP-GUMMEI                                                        PRESENCE optional}|
        { ID id-MME-UE-S1AP-ID-2                        CRITICALITY ignore        TYPE S1AP-MME-UE-S1AP-ID                                        PRESENCE optional}|
        { ID id-ManagementBasedMDTAllowed        CRITICALITY ignore        TYPE S1AP-ManagementBasedMDTAllowed                PRESENCE optional},
        ...
}








S1AP-E-RABToBeSetupListCtxtSUReq ::= SEQUENCE (SIZE(1.. s1ap-maxNrOfE-RABs)) OF ProtocolIE-SingleContainer { {S1AP-E-RABToBeSetupItemCtxtSUReqIEs} }


S1AP-E-RABToBeSetupItemCtxtSUReqIEs         S1AP-PROTOCOL-IES ::= {
        { ID id-E-RABToBeSetupItemCtxtSUReq         CRITICALITY reject         TYPE S1AP-E-RABToBeSetupItemCtxtSUReq         PRESENCE mandatory },
        ...
}


S1AP-E-RABToBeSetupItemCtxtSUReq ::= SEQUENCE {
        e-RAB-ID                                        S1AP-E-RAB-ID,
        e-RABlevelQoSParameters                                        S1AP-E-RABLevelQoSParameters,                
        transportLayerAddress                         S1AP-TransportLayerAddress,
        gTP-TEID                        S1AP-GTP-TEID,
        nAS-PDU                                S1AP-NAS-PDU                OPTIONAL,
        iE-Extensions                                        ProtocolExtensionContainer { {S1AP-E-RABToBeSetupItemCtxtSUReqExtIEs} } OPTIONAL,
        ...
}




S1AP-E-RABToBeSetupItemCtxtSUReqExtIEs S1AP-PROTOCOL-EXTENSION ::= {
        { ID id-Correlation-ID                CRITICALITY ignore        EXTENSION S1AP-Correlation-ID                PRESENCE optional},
        ...
}




-- **************************************************************
--
-- Initial Context Setup Response
--
-- **************************************************************


S1AP-InitialContextSetupResponse ::= SEQUENCE {
        protocolIEs                        ProtocolIE-Container       { {S1AP-InitialContextSetupResponseIEs} },
        ...
}


S1AP-InitialContextSetupResponseIEs S1AP-PROTOCOL-IES ::= {
        { ID id-MME-UE-S1AP-ID                                                CRITICALITY ignore        TYPE S1AP-MME-UE-S1AP-ID                                         PRESENCE mandatory }|
        { ID id-eNB-UE-S1AP-ID                                                CRITICALITY ignore        TYPE S1AP-ENB-UE-S1AP-ID                                         PRESENCE mandatory }|
        { ID id-E-RABSetupListCtxtSURes                                CRITICALITY ignore        TYPE S1AP-E-RABSetupListCtxtSURes                PRESENCE mandatory }|
        { ID id-E-RABFailedToSetupListCtxtSURes                CRITICALITY ignore        TYPE S1AP-E-RABList                                                PRESENCE optional }|
        { ID id-CriticalityDiagnostics                                CRITICALITY ignore        TYPE S1AP-CriticalityDiagnostics                        PRESENCE optional },
        ...
}




S1AP-E-RABSetupListCtxtSURes ::= SEQUENCE (SIZE(1.. s1ap-maxNrOfE-RABs)) OF ProtocolIE-SingleContainer { {S1AP-E-RABSetupItemCtxtSUResIEs} }


S1AP-E-RABSetupItemCtxtSUResIEs         S1AP-PROTOCOL-IES ::= {
        { ID id-E-RABSetupItemCtxtSURes         CRITICALITY ignore         TYPE S1AP-E-RABSetupItemCtxtSURes         PRESENCE mandatory },
        ...
}


S1AP-E-RABSetupItemCtxtSURes ::= SEQUENCE {
        e-RAB-ID                                        S1AP-E-RAB-ID,
        transportLayerAddress                         S1AP-TransportLayerAddress,
        gTP-TEID                        S1AP-GTP-TEID,
        iE-Extensions                                        ProtocolExtensionContainer { {S1AP-E-RABSetupItemCtxtSUResExtIEs} } OPTIONAL,
        ...
}




S1AP-E-RABSetupItemCtxtSUResExtIEs S1AP-PROTOCOL-EXTENSION ::= {
        ...
}




-- **************************************************************
--
-- Initial Context Setup Failure
--
-- **************************************************************


S1AP-InitialContextSetupFailure ::= SEQUENCE {
        protocolIEs                        ProtocolIE-Container       { {S1AP-InitialContextSetupFailureIEs} },
        ...
}


S1AP-InitialContextSetupFailureIEs S1AP-PROTOCOL-IES ::= {
        { ID id-MME-UE-S1AP-ID                                CRITICALITY ignore        TYPE S1AP-MME-UE-S1AP-ID                                         PRESENCE mandatory }|
        { ID id-eNB-UE-S1AP-ID                                CRITICALITY ignore        TYPE S1AP-ENB-UE-S1AP-ID                                         PRESENCE mandatory }|
        { ID id-Cause                                                CRITICALITY ignore        TYPE S1AP-Cause                                                        PRESENCE mandatory }|
        { ID id-CriticalityDiagnostics                CRITICALITY ignore        TYPE S1AP-CriticalityDiagnostics                        PRESENCE optional },
        ...
}


-- **************************************************************
--
-- PAGING ELEMENTARY PROCEDURE
--
-- **************************************************************




-- **************************************************************
--
-- S1AP-Paging
--
-- **************************************************************


S1AP-Paging ::= SEQUENCE {
        protocolIEs                        ProtocolIE-Container       {{S1AP-PagingIEs}},
        ...
}


S1AP-PagingIEs S1AP-PROTOCOL-IES ::= {
        { ID id-UEIdentityIndexValue                CRITICALITY ignore        TYPE S1AP-UEIdentityIndexValue        PRESENCE mandatory}|
        { ID id-UEPagingID                                        CRITICALITY ignore        TYPE S1AP-UEPagingID                                PRESENCE mandatory}|
        { ID id-pagingDRX                                        CRITICALITY ignore        TYPE S1AP-PagingDRX                                PRESENCE optional}|
        { ID id-CNDomain                                        CRITICALITY ignore        TYPE S1AP-CNDomain                                PRESENCE mandatory}|
        { ID id-TAIList                                                CRITICALITY ignore        TYPE S1AP-TAIList                                PRESENCE mandatory}|
        { ID id-CSG-IdList                                        CRITICALITY ignore        TYPE S1AP-CSG-IdList                                PRESENCE optional}|
        { ID id-PagingPriority                                CRITICALITY ignore        TYPE S1AP-PagingPriority                        PRESENCE optional},
        ...
}


S1AP-TAIList::= SEQUENCE (SIZE(1.. s1ap-maxnoofTAIs)) OF ProtocolIE-SingleContainer {{S1AP-TAIItemIEs}}


S1AP-TAIItemIEs         S1AP-PROTOCOL-IES ::= {
        { ID id-TAIItem         CRITICALITY ignore                TYPE S1AP-TAIItem        PRESENCE mandatory },
        ...
}


S1AP-TAIItem ::= SEQUENCE {
        tAI                                                         S1AP-TAI,
        iE-Extensions                                        ProtocolExtensionContainer { {S1AP-TAIItemExtIEs} } OPTIONAL,
        ...
}




S1AP-TAIItemExtIEs S1AP-PROTOCOL-EXTENSION ::= {
        ...
}


-- **************************************************************
--
-- UE CONTEXT RELEASE ELEMENTARY PROCEDURE
--
-- **************************************************************


-- **************************************************************
--
-- UE CONTEXT RELEASE REQUEST
--
-- **************************************************************


S1AP-UEContextReleaseRequest ::= SEQUENCE {
        protocolIEs                     ProtocolIE-Container       {{S1AP-UEContextReleaseRequest-IEs}},
        ...
}


S1AP-UEContextReleaseRequest-IEs S1AP-PROTOCOL-IES ::= {
        { ID id-MME-UE-S1AP-ID                                CRITICALITY reject        TYPE S1AP-MME-UE-S1AP-ID                                        PRESENCE mandatory}|
        { ID id-eNB-UE-S1AP-ID                                CRITICALITY reject        TYPE S1AP-ENB-UE-S1AP-ID                                        PRESENCE mandatory}|
        { ID id-Cause                                                CRITICALITY ignore        TYPE S1AP-Cause                                                        PRESENCE mandatory}|
        { ID id-GWContextReleaseIndication        CRITICALITY reject        TYPE S1AP-GWContextReleaseIndication                PRESENCE optional},
        ...
}


-- **************************************************************
--
-- UE Context Release Command
--
-- **************************************************************


S1AP-UEContextReleaseCommand ::= SEQUENCE {
        protocolIEs                     ProtocolIE-Container       {{S1AP-UEContextReleaseCommand-IEs}},
        ...
}


S1AP-UEContextReleaseCommand-IEs S1AP-PROTOCOL-IES ::= {
        { ID id-UE-S1AP-IDs                                CRITICALITY reject        TYPE S1AP-UE-S1AP-IDs                                        PRESENCE mandatory} |
        
        { ID id-Cause                                        CRITICALITY ignore        TYPE S1AP-Cause                                                PRESENCE mandatory} ,
        ...
}


-- **************************************************************
--
-- UE Context Release Complete
--
-- **************************************************************


S1AP-UEContextReleaseComplete ::= SEQUENCE {
        protocolIEs                     ProtocolIE-Container       {{S1AP-UEContextReleaseComplete-IEs}},
        ...
}


S1AP-UEContextReleaseComplete-IEs S1AP-PROTOCOL-IES ::= {
        { ID id-MME-UE-S1AP-ID                                CRITICALITY ignore        TYPE S1AP-MME-UE-S1AP-ID                                PRESENCE mandatory} |
        { ID id-eNB-UE-S1AP-ID                                CRITICALITY ignore        TYPE S1AP-ENB-UE-S1AP-ID                                PRESENCE mandatory} |
        { ID id-CriticalityDiagnostics                CRITICALITY ignore        TYPE S1AP-CriticalityDiagnostics                PRESENCE optional },
        ...
}




-- **************************************************************
--
-- UE CONTEXT MODIFICATION ELEMENTARY PROCEDURE
--
-- **************************************************************


-- **************************************************************
--
-- UE Context Modification Request
--
-- **************************************************************


S1AP-UEContextModificationRequest ::= SEQUENCE {
        protocolIEs                        ProtocolIE-Container       { { S1AP-UEContextModificationRequestIEs} },
        ...
}


S1AP-UEContextModificationRequestIEs S1AP-PROTOCOL-IES ::= {        
        { ID id-MME-UE-S1AP-ID                                CRITICALITY reject        TYPE S1AP-MME-UE-S1AP-ID                                         PRESENCE mandatory}|
        { ID id-eNB-UE-S1AP-ID                                CRITICALITY reject        TYPE S1AP-ENB-UE-S1AP-ID                                        PRESENCE mandatory}|
        { ID id-SecurityKey                                        CRITICALITY reject        TYPE S1AP-SecurityKey                                         PRESENCE optional}|
        { ID id-SubscriberProfileIDforRFP        CRITICALITY ignore        TYPE S1AP-SubscriberProfileIDforRFP                PRESENCE optional}|
        { ID id-uEaggregateMaximumBitrate        CRITICALITY ignore        TYPE S1AP-UEAggregateMaximumBitrate                PRESENCE optional}|
        { ID id-CSFallbackIndicator                        CRITICALITY reject        TYPE S1AP-CSFallbackIndicator                        PRESENCE optional}|
        { ID id-UESecurityCapabilities                CRITICALITY reject        TYPE S1AP-UESecurityCapabilities                        PRESENCE optional}|
        { ID id-CSGMembershipStatus                        CRITICALITY ignore        TYPE S1AP-CSGMembershipStatus                        PRESENCE optional}|
        { ID id-RegisteredLAI                                CRITICALITY ignore        TYPE S1AP-LAI                                                        PRESENCE optional},
        ...
}
-- **************************************************************
--
-- UE Context Modification Response
--
-- **************************************************************


S1AP-UEContextModificationResponse ::= SEQUENCE {
        protocolIEs                        ProtocolIE-Container       { { S1AP-UEContextModificationResponseIEs} },
        ...
}


S1AP-UEContextModificationResponseIEs S1AP-PROTOCOL-IES ::= {        
        { ID id-MME-UE-S1AP-ID                                CRITICALITY ignore        TYPE S1AP-MME-UE-S1AP-ID                                PRESENCE mandatory }|
        { ID id-eNB-UE-S1AP-ID                                CRITICALITY ignore        TYPE S1AP-ENB-UE-S1AP-ID                                PRESENCE mandatory }|
        { ID id-CriticalityDiagnostics                CRITICALITY ignore        TYPE S1AP-CriticalityDiagnostics                PRESENCE optional },
        ...
}-- **************************************************************
--
-- UE Context Modification Failure
--
-- **************************************************************


S1AP-UEContextModificationFailure ::= SEQUENCE {
        protocolIEs                        ProtocolIE-Container       { { S1AP-UEContextModificationFailureIEs} },
        ...
}


S1AP-UEContextModificationFailureIEs S1AP-PROTOCOL-IES ::= {        
        { ID id-MME-UE-S1AP-ID                                CRITICALITY ignore        TYPE S1AP-MME-UE-S1AP-ID                                PRESENCE mandatory }|
        { ID id-eNB-UE-S1AP-ID                                CRITICALITY ignore        TYPE S1AP-ENB-UE-S1AP-ID                                PRESENCE mandatory }|
        { ID id-Cause                                                CRITICALITY ignore        TYPE S1AP-Cause                                                PRESENCE mandatory }|
        { ID id-CriticalityDiagnostics                CRITICALITY ignore        TYPE S1AP-CriticalityDiagnostics                PRESENCE optional },
        ...
}


-- **************************************************************
--
-- NAS TRANSPORT ELEMENTARY PROCEDURES
--
-- **************************************************************


-- **************************************************************
--
-- DOWNLINK NAS TRANSPORT
--
-- **************************************************************


S1AP-DownlinkNASTransport ::= SEQUENCE {
        protocolIEs                     ProtocolIE-Container       {{S1AP-DownlinkNASTransport-IEs}},
        ...
}


S1AP-DownlinkNASTransport-IEs S1AP-PROTOCOL-IES ::= {
        { ID id-MME-UE-S1AP-ID                                CRITICALITY reject        TYPE S1AP-MME-UE-S1AP-ID                                        PRESENCE mandatory} |
        { ID id-eNB-UE-S1AP-ID                                CRITICALITY reject        TYPE S1AP-ENB-UE-S1AP-ID                                        PRESENCE mandatory} |
        { ID id-NAS-PDU                                                CRITICALITY reject        TYPE S1AP-NAS-PDU                                                PRESENCE mandatory} |
        { ID id-HandoverRestrictionList                CRITICALITY ignore        TYPE S1AP-HandoverRestrictionList                PRESENCE optional} |
        { ID id-SubscriberProfileIDforRFP        CRITICALITY ignore        TYPE S1AP-SubscriberProfileIDforRFP                PRESENCE optional},
        ...
}




-- **************************************************************
--
-- INITIAL UE MESSAGE
--
-- **************************************************************


S1AP-InitialUEMessage ::= SEQUENCE {
        protocolIEs                     ProtocolIE-Container       {{S1AP-InitialUEMessage-IEs}},
        ...
}


S1AP-InitialUEMessage-IEs S1AP-PROTOCOL-IES ::= {
        { ID id-eNB-UE-S1AP-ID                                CRITICALITY reject        TYPE S1AP-ENB-UE-S1AP-ID                                        PRESENCE mandatory} |
        { ID id-NAS-PDU                                                CRITICALITY reject        TYPE S1AP-NAS-PDU                                                PRESENCE mandatory} |
        { ID id-TAI                                                        CRITICALITY reject        TYPE S1AP-TAI                                                        PRESENCE mandatory} |
        { ID id-EUTRAN-CGI                                        CRITICALITY ignore        TYPE S1AP-EUTRAN-CGI                                                PRESENCE mandatory} |
        { ID id-RRC-Establishment-Cause                CRITICALITY ignore        TYPE S1AP-RRC-Establishment-Cause                PRESENCE mandatory} |
        { ID id-S-TMSI                                                CRITICALITY reject        TYPE S1AP-S-TMSI                                                        PRESENCE optional} |
        { ID id-CSG-Id                                                CRITICALITY reject        TYPE S1AP-CSG-Id                                                        PRESENCE optional} |
        { ID id-GUMMEI-ID                                        CRITICALITY reject        TYPE S1AP-GUMMEI                                                        PRESENCE optional} |
        { ID id-CellAccessMode                                CRITICALITY reject        TYPE S1AP-CellAccessMode                                        PRESENCE optional} |
        { ID id-GW-TransportLayerAddress        CRITICALITY ignore        TYPE S1AP-TransportLayerAddress                        PRESENCE optional} |
        { ID id-RelayNode-Indicator                        CRITICALITY reject        TYPE S1AP-RelayNode-Indicator                        PRESENCE optional} |
        { ID id-GUMMEIType					CRITICALITY ignore	TYPE S1AP-GUMMEIType						PRESENCE optional},
        ...
}




-- **************************************************************
--
-- UPLINK NAS TRANSPORT
--
-- **************************************************************


S1AP-UplinkNASTransport ::= SEQUENCE {
        protocolIEs                     ProtocolIE-Container       {{S1AP-UplinkNASTransport-IEs}},
        ...
}


S1AP-UplinkNASTransport-IEs S1AP-PROTOCOL-IES ::= {
        { ID id-MME-UE-S1AP-ID                                CRITICALITY reject        TYPE S1AP-MME-UE-S1AP-ID                                PRESENCE mandatory} |
        { ID id-eNB-UE-S1AP-ID                                CRITICALITY reject        TYPE S1AP-ENB-UE-S1AP-ID                                PRESENCE mandatory} |
        { ID id-NAS-PDU                                                CRITICALITY reject        TYPE S1AP-NAS-PDU                                        PRESENCE mandatory} |
        { ID id-EUTRAN-CGI                                        CRITICALITY ignore        TYPE S1AP-EUTRAN-CGI                                        PRESENCE mandatory} |
        { ID id-TAI                                                        CRITICALITY ignore        TYPE S1AP-TAI                                                PRESENCE mandatory} |
        { ID id-GW-TransportLayerAddress        CRITICALITY ignore        TYPE S1AP-TransportLayerAddress                PRESENCE optional},
        ...
}
-- **************************************************************
--
-- NAS NON DELIVERY INDICATION
--
-- **************************************************************


S1AP-NASNonDeliveryIndication ::= SEQUENCE {
        protocolIEs                     ProtocolIE-Container       {{S1AP-NASNonDeliveryIndication-IEs}},
        ...
}


S1AP-NASNonDeliveryIndication-IEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-NAS-PDU                                        CRITICALITY ignore        TYPE S1AP-NAS-PDU                                PRESENCE mandatory} |
        { ID id-Cause                                        CRITICALITY ignore        TYPE S1AP-Cause                                PRESENCE mandatory} ,
        ...
}


-- **************************************************************
--
-- RESET ELEMENTARY PROCEDURE
--
-- **************************************************************


-- **************************************************************
--
-- S1AP-Reset
--
-- **************************************************************


S1AP-Reset ::= SEQUENCE {
        protocolIEs                        ProtocolIE-Container       { {S1AP-ResetIEs} },
        ...
}


S1AP-ResetIEs S1AP-PROTOCOL-IES ::= {
        { ID id-Cause                                                CRITICALITY ignore        TYPE S1AP-Cause                                                PRESENCE mandatory        }|
        { ID id-ResetType                                CRITICALITY reject        TYPE S1AP-ResetType                        PRESENCE mandatory        },
        ...
}


S1AP-ResetType ::= CHOICE {
        s1-Interface                S1AP-ResetAll,
        partOfS1-Interface                S1AP-UE-associatedLogicalS1-ConnectionListRes,
        ...
}






S1AP-ResetAll ::= ENUMERATED {
        reset-all,
        ...
}


S1AP-UE-associatedLogicalS1-ConnectionListRes ::= SEQUENCE (SIZE(1.. s1ap-maxNrOfIndividualS1ConnectionsToReset)) OF ProtocolIE-SingleContainer { { S1AP-UE-associatedLogicalS1-ConnectionItemRes } }


S1AP-UE-associatedLogicalS1-ConnectionItemRes         S1AP-PROTOCOL-IES ::= {
        { ID id-UE-associatedLogicalS1-ConnectionItem         CRITICALITY reject         TYPE S1AP-UE-associatedLogicalS1-ConnectionItem         PRESENCE mandatory },
        ...
}




-- **************************************************************
--
-- S1AP-Reset Acknowledge
--
-- **************************************************************


S1AP-ResetAcknowledge ::= SEQUENCE {
        protocolIEs                        ProtocolIE-Container       { {S1AP-ResetAcknowledgeIEs} },
        ...
}


S1AP-ResetAcknowledgeIEs S1AP-PROTOCOL-IES ::= {
        { ID id-UE-associatedLogicalS1-ConnectionListResAck                CRITICALITY ignore        TYPE S1AP-UE-associatedLogicalS1-ConnectionListResAck                        PRESENCE optional        }|
        { ID id-CriticalityDiagnostics                CRITICALITY ignore        TYPE S1AP-CriticalityDiagnostics                        PRESENCE optional        },
        ...
}


S1AP-UE-associatedLogicalS1-ConnectionListResAck ::= SEQUENCE (SIZE(1.. s1ap-maxNrOfIndividualS1ConnectionsToReset)) OF ProtocolIE-SingleContainer { { S1AP-UE-associatedLogicalS1-ConnectionItemResAck } }


S1AP-UE-associatedLogicalS1-ConnectionItemResAck         S1AP-PROTOCOL-IES ::= {
        { ID id-UE-associatedLogicalS1-ConnectionItem         CRITICALITY ignore         TYPE S1AP-UE-associatedLogicalS1-ConnectionItem          PRESENCE mandatory },
        ...
}


-- **************************************************************
--
-- ERROR INDICATION ELEMENTARY PROCEDURE
--
-- **************************************************************


-- **************************************************************
--
-- Error Indication
--
-- **************************************************************


S1AP-ErrorIndication ::= SEQUENCE {
        protocolIEs                        ProtocolIE-Container       {{S1AP-ErrorIndicationIEs}},
        ...
}


S1AP-ErrorIndicationIEs S1AP-PROTOCOL-IES ::= {
        { ID id-MME-UE-S1AP-ID                                CRITICALITY ignore        TYPE S1AP-MME-UE-S1AP-ID                                PRESENCE optional        } |
        { ID id-eNB-UE-S1AP-ID                                CRITICALITY ignore        TYPE S1AP-ENB-UE-S1AP-ID                                PRESENCE optional        } |
        { ID id-Cause                                                CRITICALITY ignore        TYPE S1AP-Cause                                                PRESENCE optional        } |
        { ID id-CriticalityDiagnostics                CRITICALITY ignore        TYPE S1AP-CriticalityDiagnostics                PRESENCE optional        } ,
        ...
}


-- **************************************************************
--
-- S1 SETUP ELEMENTARY PROCEDURE
--
-- **************************************************************


-- **************************************************************
--
-- S1 Setup Request
--
-- **************************************************************


S1AP-S1SetupRequest ::= SEQUENCE {
        protocolIEs                        ProtocolIE-Container       { {S1AP-S1SetupRequestIEs} },
        ...
}


S1AP-S1SetupRequestIEs S1AP-PROTOCOL-IES ::= {
        { ID id-Global-ENB-ID        CRITICALITY reject        TYPE S1AP-Global-ENB-ID        PRESENCE mandatory}|
        { ID id-eNBname        CRITICALITY ignore        TYPE S1AP-ENBname        PRESENCE optional}|
        { ID id-SupportedTAs        CRITICALITY reject        TYPE S1AP-SupportedTAs        PRESENCE mandatory}|
        { ID id-DefaultPagingDRX        CRITICALITY ignore        TYPE S1AP-PagingDRX        PRESENCE mandatory}|
        { ID id-CSG-IdList        CRITICALITY reject        TYPE S1AP-CSG-IdList        PRESENCE optional},
        ...
}


-- **************************************************************
--
-- S1 Setup Response
--
-- **************************************************************


S1AP-S1SetupResponse ::= SEQUENCE {
        protocolIEs                        ProtocolIE-Container       { {S1AP-S1SetupResponseIEs} },
        ...
}




S1AP-S1SetupResponseIEs S1AP-PROTOCOL-IES ::= {
        { ID id-MMEname                                                CRITICALITY ignore        TYPE S1AP-MMEname                                                PRESENCE optional}|
        { ID id-ServedGUMMEIs                                CRITICALITY reject        TYPE S1AP-ServedGUMMEIs                                        PRESENCE mandatory}|
        { ID id-RelativeMMECapacity                        CRITICALITY ignore        TYPE S1AP-RelativeMMECapacity                        PRESENCE mandatory}|
        { ID id-MMERelaySupportIndicator        CRITICALITY ignore        TYPE S1AP-MMERelaySupportIndicator                PRESENCE optional}|
        { ID id-CriticalityDiagnostics                CRITICALITY ignore        TYPE S1AP-CriticalityDiagnostics                        PRESENCE optional},
        ...
}


-- **************************************************************
--
-- S1 Setup Failure
--
-- **************************************************************


S1AP-S1SetupFailure ::= SEQUENCE {
        protocolIEs                        ProtocolIE-Container       { {S1AP-S1SetupFailureIEs} },
        ...
}


S1AP-S1SetupFailureIEs S1AP-PROTOCOL-IES ::= {
        { ID id-Cause                                                CRITICALITY ignore        TYPE S1AP-Cause                                                PRESENCE mandatory        }|
        { ID id-TimeToWait                                        CRITICALITY ignore        TYPE S1AP-TimeToWait                                        PRESENCE optional        }|
        { ID id-CriticalityDiagnostics                CRITICALITY ignore        TYPE S1AP-CriticalityDiagnostics                        PRESENCE optional        },
        ...
}


-- **************************************************************
--
-- ENB CONFIGURATION UPDATE ELEMENTARY PROCEDURE
--
-- **************************************************************


-- **************************************************************
--
-- eNB Configuration Update 
--
-- **************************************************************


S1AP-ENBConfigurationUpdate ::= SEQUENCE {
        protocolIEs                        ProtocolIE-Container       { {S1AP-ENBConfigurationUpdateIEs} },
        ...
}


S1AP-ENBConfigurationUpdateIEs S1AP-PROTOCOL-IES ::= {
        { ID id-eNBname                                CRITICALITY ignore        TYPE S1AP-ENBname                        PRESENCE optional        }|
        { ID id-SupportedTAs                CRITICALITY reject        TYPE S1AP-SupportedTAs                 PRESENCE optional        }|
        { ID id-CSG-IdList                                        CRITICALITY reject        TYPE S1AP-CSG-IdList                                PRESENCE optional}|
        { ID id-DefaultPagingDRX        CRITICALITY        ignore        TYPE S1AP-PagingDRX                PRESENCE optional        },
        ...
}


-- **************************************************************
--
-- eNB Configuration Update Acknowledge
--
-- **************************************************************


S1AP-ENBConfigurationUpdateAcknowledge ::= SEQUENCE {
        protocolIEs                        ProtocolIE-Container       { {S1AP-ENBConfigurationUpdateAcknowledgeIEs} },
        ...
}




S1AP-ENBConfigurationUpdateAcknowledgeIEs S1AP-PROTOCOL-IES ::= {
        { ID id-CriticalityDiagnostics                CRITICALITY ignore        TYPE S1AP-CriticalityDiagnostics                        PRESENCE optional        },
        ...
}


-- **************************************************************
--
-- eNB Configuration Update Failure
--
-- **************************************************************


S1AP-ENBConfigurationUpdateFailure ::= SEQUENCE {
        protocolIEs                        ProtocolIE-Container       { {S1AP-ENBConfigurationUpdateFailureIEs} },
        ...
}


S1AP-ENBConfigurationUpdateFailureIEs S1AP-PROTOCOL-IES ::= {
        { ID id-Cause                                                CRITICALITY ignore        TYPE S1AP-Cause                                                PRESENCE mandatory        }|
        { ID id-TimeToWait                                        CRITICALITY ignore        TYPE S1AP-TimeToWait                                        PRESENCE optional        }|
        { ID id-CriticalityDiagnostics                CRITICALITY ignore        TYPE S1AP-CriticalityDiagnostics        PRESENCE optional },
...
}




-- **************************************************************
--
-- MME Configuration UPDATE ELEMENTARY PROCEDURE
--
-- **************************************************************


-- **************************************************************
--
-- MME Configuration Update 
--
-- **************************************************************


S1AP-MMEConfigurationUpdate ::= SEQUENCE {
        protocolIEs                        ProtocolIE-Container       { {S1AP-MMEConfigurationUpdateIEs} },
        ...
}


S1AP-MMEConfigurationUpdateIEs S1AP-PROTOCOL-IES ::= {
        { ID id-MMEname                                CRITICALITY ignore        TYPE S1AP-MMEname                         PRESENCE optional        }|
        { ID id-ServedGUMMEIs                        CRITICALITY reject        TYPE S1AP-ServedGUMMEIs                                PRESENCE optional        }|
        { ID id-RelativeMMECapacity        CRITICALITY reject        TYPE S1AP-RelativeMMECapacity        PRESENCE optional},
        ...
}


-- **************************************************************
--
-- MME Configuration Update Acknowledge
--
-- **************************************************************


S1AP-MMEConfigurationUpdateAcknowledge ::= SEQUENCE {
        protocolIEs                        ProtocolIE-Container       { {S1AP-MMEConfigurationUpdateAcknowledgeIEs} },
        ...
}




S1AP-MMEConfigurationUpdateAcknowledgeIEs S1AP-PROTOCOL-IES ::= {
        { ID id-CriticalityDiagnostics                CRITICALITY ignore        TYPE S1AP-CriticalityDiagnostics                        PRESENCE optional        },
        ...
}


-- **************************************************************
--
-- MME Configuration Update Failure
--
-- **************************************************************


S1AP-MMEConfigurationUpdateFailure ::= SEQUENCE {
        protocolIEs                        ProtocolIE-Container       { {S1AP-MMEConfigurationUpdateFailureIEs} },
        ...
}


S1AP-MMEConfigurationUpdateFailureIEs S1AP-PROTOCOL-IES ::= {
        { ID id-Cause                                                CRITICALITY ignore        TYPE S1AP-Cause                                                PRESENCE mandatory        }|
        { ID id-TimeToWait                                        CRITICALITY ignore        TYPE S1AP-TimeToWait                                        PRESENCE optional        }|
        { ID id-CriticalityDiagnostics                CRITICALITY ignore        TYPE S1AP-CriticalityDiagnostics                        PRESENCE optional        },
        ...
}


-- **************************************************************
--
-- DOWNLINK S1 CDMA2000 TUNNELING ELEMENTARY PROCEDURE
--
-- **************************************************************


-- **************************************************************
--
-- Downlink S1 CDMA2000 Tunneling
--
-- **************************************************************


S1AP-DownlinkS1cdma2000tunneling ::= SEQUENCE {
        protocolIEs                        ProtocolIE-Container       { {S1AP-DownlinkS1cdma2000tunnelingIEs} },
        ...
}


S1AP-DownlinkS1cdma2000tunnelingIEs S1AP-PROTOCOL-IES ::= {
        { ID id-MME-UE-S1AP-ID                                CRITICALITY reject        TYPE S1AP-MME-UE-S1AP-ID                                PRESENCE mandatory        } |
        { ID id-eNB-UE-S1AP-ID                                CRITICALITY reject        TYPE S1AP-ENB-UE-S1AP-ID                                PRESENCE mandatory        } |
        { ID id-E-RABSubjecttoDataForwardingList                CRITICALITY ignore        TYPE S1AP-E-RABSubjecttoDataForwardingList                                         PRESENCE optional        } |
        { ID id-cdma2000HOStatus                                CRITICALITY ignore        TYPE S1AP-Cdma2000HOStatus                         PRESENCE optional        } |
        { ID id-cdma2000RATType                                CRITICALITY reject        TYPE S1AP-Cdma2000RATType                         PRESENCE mandatory        } |
        { ID id-cdma2000PDU                                        CRITICALITY reject        TYPE S1AP-Cdma2000PDU                                 PRESENCE mandatory        },
        ...
}


-- **************************************************************
--
-- UPLINK S1 CDMA2000 TUNNELING ELEMENTARY PROCEDURE
--
-- **************************************************************


-- **************************************************************
--
-- Uplink S1 CDMA2000 Tunneling
--
-- **************************************************************


S1AP-UplinkS1cdma2000tunneling ::= SEQUENCE {
        protocolIEs                        ProtocolIE-Container       { {S1AP-UplinkS1cdma2000tunnelingIEs} },
        ...
}


S1AP-UplinkS1cdma2000tunnelingIEs S1AP-PROTOCOL-IES ::= {
        { ID id-MME-UE-S1AP-ID                                CRITICALITY reject        TYPE S1AP-MME-UE-S1AP-ID                                PRESENCE mandatory        } |
        { ID id-eNB-UE-S1AP-ID                                CRITICALITY reject        TYPE S1AP-ENB-UE-S1AP-ID                                PRESENCE mandatory        } |
        { ID id-cdma2000RATType                                CRITICALITY reject        TYPE S1AP-Cdma2000RATType                         PRESENCE mandatory        } |
        { ID id-cdma2000SectorID                        CRITICALITY reject        TYPE S1AP-Cdma2000SectorID                         PRESENCE mandatory        } |
        { ID id-cdma2000HORequiredIndication        CRITICALITY ignore        TYPE S1AP-Cdma2000HORequiredIndication                         PRESENCE optional        } |
        { ID id-cdma2000OneXSRVCCInfo                CRITICALITY reject        TYPE S1AP-Cdma2000OneXSRVCCInfo                         PRESENCE optional        } |
        { ID id-cdma2000OneXRAND                        CRITICALITY reject        TYPE S1AP-Cdma2000OneXRAND                         PRESENCE optional        } |
        { ID id-cdma2000PDU                                        CRITICALITY reject        TYPE S1AP-Cdma2000PDU                                 PRESENCE mandatory        }|
        { ID id-EUTRANRoundTripDelayEstimationInfo        CRITICALITY ignore        TYPE S1AP-EUTRANRoundTripDelayEstimationInfo                PRESENCE optional},
        -- Extension for Release 9 to assist target HRPD access with the acquisition of the UE --
        ...
}




-- **************************************************************
--
-- UE CAPABILITY INFO INDICATION ELEMENTARY PROCEDURE
--
-- **************************************************************


-- **************************************************************
--
-- UE Capability Info Indication
--
-- **************************************************************


S1AP-UECapabilityInfoIndication ::= SEQUENCE {
        protocolIEs                        ProtocolIE-Container       { { S1AP-UECapabilityInfoIndicationIEs} },
        ...
}


S1AP-UECapabilityInfoIndicationIEs S1AP-PROTOCOL-IES ::= {
        { ID id-MME-UE-S1AP-ID                                CRITICALITY reject        TYPE S1AP-MME-UE-S1AP-ID                                         PRESENCE mandatory        } |
        { ID id-eNB-UE-S1AP-ID                                CRITICALITY reject        TYPE S1AP-ENB-UE-S1AP-ID                                         PRESENCE mandatory        } |
        { ID id-UERadioCapability                        CRITICALITY ignore        TYPE S1AP-UERadioCapability                                PRESENCE mandatory        } ,
        ...
}


-- **************************************************************
--
-- eNB STATUS TRANSFER ELEMENTARY PROCEDURE
--
-- **************************************************************


-- **************************************************************
--
-- eNB Status Transfer
--
-- **************************************************************


S1AP-ENBStatusTransfer ::= SEQUENCE {
        protocolIEs                        ProtocolIE-Container       { {S1AP-ENBStatusTransferIEs} },
        ...
}


S1AP-ENBStatusTransferIEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-eNB-StatusTransfer-TransparentContainer        CRITICALITY reject        TYPE S1AP-ENB-StatusTransfer-TransparentContainer                PRESENCE mandatory} ,
        ...
}




-- **************************************************************
--
-- MME STATUS TRANSFER ELEMENTARY PROCEDURE
--
-- **************************************************************


-- **************************************************************
--
-- MME Status Transfer
--
-- **************************************************************


S1AP-MMEStatusTransfer ::= SEQUENCE {
        protocolIEs                        ProtocolIE-Container       { {S1AP-MMEStatusTransferIEs} },
        ...
}


S1AP-MMEStatusTransferIEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-eNB-StatusTransfer-TransparentContainer        CRITICALITY reject        TYPE S1AP-ENB-StatusTransfer-TransparentContainer                PRESENCE mandatory} ,
        ...
}




-- **************************************************************
--
-- TRACE ELEMENTARY PROCEDURES
--
-- **************************************************************
-- **************************************************************
--
-- Trace Start
--
-- **************************************************************


S1AP-TraceStart ::= SEQUENCE {
        protocolIEs                        ProtocolIE-Container       { {S1AP-TraceStartIEs} },
        ...
}


S1AP-TraceStartIEs S1AP-PROTOCOL-IES ::= {
        { ID id-MME-UE-S1AP-ID                                CRITICALITY reject        TYPE S1AP-MME-UE-S1AP-ID                                PRESENCE mandatory} |
        { ID id-eNB-UE-S1AP-ID                                CRITICALITY reject        TYPE S1AP-ENB-UE-S1AP-ID                                PRESENCE mandatory} |
        { ID id-TraceActivation                                CRITICALITY ignore        TYPE S1AP-TraceActivation                        PRESENCE mandatory        },
        ...
}


-- **************************************************************
--
-- Trace Failure Indication
--
-- **************************************************************


S1AP-TraceFailureIndication ::= SEQUENCE {
        protocolIEs                        ProtocolIE-Container       { {S1AP-TraceFailureIndicationIEs} },
        ...
}


S1AP-TraceFailureIndicationIEs S1AP-PROTOCOL-IES ::= {
        { ID id-MME-UE-S1AP-ID                                CRITICALITY reject        TYPE S1AP-MME-UE-S1AP-ID                                PRESENCE mandatory} |
        { ID id-eNB-UE-S1AP-ID                                CRITICALITY reject        TYPE S1AP-ENB-UE-S1AP-ID                                PRESENCE mandatory} |
        { ID id-E-UTRAN-Trace-ID                        CRITICALITY ignore        TYPE S1AP-E-UTRAN-Trace-ID                        PRESENCE mandatory} |
        { ID id-Cause                                                CRITICALITY ignore        TYPE S1AP-Cause                                                PRESENCE mandatory} ,
        ...
}


-- **************************************************************
--
-- DEACTIVATE TRACE ELEMENTARY PROCEDURE
--
-- **************************************************************


-- **************************************************************
--
-- DEACTIVATE TRACE
--
-- **************************************************************


S1AP-DeactivateTrace ::= SEQUENCE {
        protocolIEs                        ProtocolIE-Container       { { S1AP-DeactivateTraceIEs} },
        ...
}


S1AP-DeactivateTraceIEs S1AP-PROTOCOL-IES ::= {
        { ID id-MME-UE-S1AP-ID                CRITICALITY reject        TYPE S1AP-MME-UE-S1AP-ID                PRESENCE mandatory} |
        { ID id-eNB-UE-S1AP-ID                CRITICALITY reject        TYPE S1AP-ENB-UE-S1AP-ID                PRESENCE mandatory} |
        { ID id-E-UTRAN-Trace-ID                CRITICALITY ignore        TYPE S1AP-E-UTRAN-Trace-ID                 PRESENCE mandatory        },
        ...
}


-- **************************************************************
--
-- CELL TRAFFIC TRACE ELEMENTARY PROCEDURE
--
-- **************************************************************


-- **************************************************************
--
-- CELL TRAFFIC TRACE
--
-- **************************************************************


S1AP-CellTrafficTrace ::= SEQUENCE {
     protocolIEs                ProtocolIE-Container        { { S1AP-CellTrafficTraceIEs } },
     ...
}


S1AP-CellTrafficTraceIEs S1AP-PROTOCOL-IES ::= {
        {ID id-MME-UE-S1AP-ID                                        CRITICALITY reject        TYPE S1AP-MME-UE-S1AP-ID                                PRESENCE mandatory}|
        {ID id-eNB-UE-S1AP-ID                                        CRITICALITY reject        TYPE S1AP-ENB-UE-S1AP-ID                                PRESENCE mandatory}|
        {ID id-E-UTRAN-Trace-ID                                        CRITICALITY ignore        TYPE S1AP-E-UTRAN-Trace-ID                        PRESENCE mandatory}|
        {ID id-EUTRAN-CGI                                                CRITICALITY ignore        TYPE S1AP-EUTRAN-CGI                                        PRESENCE mandatory}|
        {ID id-TraceCollectionEntityIPAddress        CRITICALITY ignore        TYPE S1AP-TransportLayerAddress                PRESENCE mandatory}|
        {ID id-PrivacyIndicator                                        CRITICALITY ignore        TYPE S1AP-PrivacyIndicator                        PRESENCE optional},
        ...
}


-- **************************************************************
--
-- LOCATION ELEMENTARY PROCEDURES
--
-- **************************************************************


-- **************************************************************
--
-- Location Reporting Control
--
-- **************************************************************


S1AP-LocationReportingControl ::= SEQUENCE {
        protocolIEs                        ProtocolIE-Container       { { S1AP-LocationReportingControlIEs} },
        ...
}


S1AP-LocationReportingControlIEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-RequestType                                CRITICALITY ignore        TYPE S1AP-RequestType                                PRESENCE mandatory        } ,
        ...
}


-- **************************************************************
--
-- Location Report Failure Indication
--
-- **************************************************************


S1AP-LocationReportingFailureIndication ::= SEQUENCE {
        protocolIEs                        ProtocolIE-Container       { { S1AP-LocationReportingFailureIndicationIEs} },
        ...
}


S1AP-LocationReportingFailureIndicationIEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-Cause                                        CRITICALITY ignore        TYPE S1AP-Cause                                                PRESENCE mandatory},
        ...
}


-- **************************************************************
--
-- Location Report 
--
-- **************************************************************


S1AP-LocationReport ::= SEQUENCE {
        protocolIEs                        ProtocolIE-Container       { { S1AP-LocationReportIEs} },
        ...
}


S1AP-LocationReportIEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-EUTRAN-CGI                                CRITICALITY ignore        TYPE S1AP-EUTRAN-CGI                                        PRESENCE mandatory} |
        { ID id-TAI                                                CRITICALITY ignore        TYPE S1AP-TAI                                                PRESENCE mandatory} |
        { ID id-RequestType                                CRITICALITY ignore        TYPE S1AP-RequestType                                PRESENCE mandatory} ,
        ...
}


-- **************************************************************
--
-- OVERLOAD ELEMENTARY PROCEDURES
--
-- **************************************************************


-- **************************************************************
--
-- Overload Start
--
-- **************************************************************


S1AP-OverloadStart ::= SEQUENCE {
        protocolIEs                        ProtocolIE-Container       { {S1AP-OverloadStartIEs} },
        ...
}


S1AP-OverloadStartIEs S1AP-PROTOCOL-IES ::= {        
        { ID id-OverloadResponse                                        CRITICALITY reject        TYPE S1AP-OverloadResponse                                PRESENCE mandatory}|
        { ID id-GUMMEIList                                                        CRITICALITY ignore        TYPE S1AP-GUMMEIList                                                PRESENCE optional}|
        { ID id-TrafficLoadReductionIndication                CRITICALITY ignore        TYPE S1AP-TrafficLoadReductionIndication        PRESENCE optional},
        ...
}
-- **************************************************************
--
-- Overload Stop
--
-- **************************************************************


S1AP-OverloadStop ::= SEQUENCE {
        protocolIEs                        ProtocolIE-Container       { {S1AP-OverloadStopIEs} },
        ...
}


S1AP-OverloadStopIEs S1AP-PROTOCOL-IES ::= {        
{ ID id-GUMMEIList                                                        CRITICALITY ignore        TYPE S1AP-GUMMEIList                                PRESENCE optional },
        ...
}
-- **************************************************************
--
-- WRITE-REPLACE WARNING ELEMENTARY PROCEDURE 
--
-- **************************************************************


-- **************************************************************
--
-- Write-Replace Warning Request
--
-- **************************************************************




S1AP-WriteReplaceWarningRequest ::= SEQUENCE {
        protocolIEs                        ProtocolIE-Container       { {S1AP-WriteReplaceWarningRequestIEs} },
        ...
}


S1AP-WriteReplaceWarningRequestIEs S1AP-PROTOCOL-IES ::= {        
        { ID id-MessageIdentifier                        CRITICALITY reject        TYPE S1AP-MessageIdentifier                PRESENCE mandatory                }|
        { ID id-SerialNumber                                CRITICALITY reject        TYPE S1AP-SerialNumber                        PRESENCE mandatory                }|
        { ID id-WarningAreaList                                CRITICALITY ignore        TYPE S1AP-WarningAreaList                PRESENCE optional                }|
        { ID id-RepetitionPeriod                        CRITICALITY reject        TYPE S1AP-RepetitionPeriod                PRESENCE mandatory                }|
        { ID id-ExtendedRepetitionPeriod        CRITICALITY reject        TYPE S1AP-ExtendedRepetitionPeriod        PRESENCE optional        }|
        { ID id-NumberofBroadcastRequest        CRITICALITY reject        TYPE S1AP-NumberofBroadcastRequest        PRESENCE mandatory        }|
        { ID id-WarningType                                        CRITICALITY ignore        TYPE S1AP-WarningType                        PRESENCE optional                }|
        { ID id-WarningSecurityInfo                        CRITICALITY ignore        TYPE S1AP-WarningSecurityInfo        PRESENCE optional                }|
        { ID id-DataCodingScheme                        CRITICALITY ignore        TYPE S1AP-DataCodingScheme                PRESENCE optional                }|
        { ID id-WarningMessageContents                CRITICALITY ignore        TYPE S1AP-WarningMessageContents                PRESENCE optional                }|
        { ID id-ConcurrentWarningMessageIndicator        CRITICALITY reject        TYPE S1AP-ConcurrentWarningMessageIndicator                PRESENCE optional                },
        ...
}
-- **************************************************************
--
-- Write-Replace Warning Response
--
-- **************************************************************


S1AP-WriteReplaceWarningResponse ::= SEQUENCE {
        protocolIEs                        ProtocolIE-Container                { {S1AP-WriteReplaceWarningResponseIEs} },
        ...
}


S1AP-WriteReplaceWarningResponseIEs S1AP-PROTOCOL-IES ::= {
        { ID id-MessageIdentifier                        CRITICALITY reject        TYPE S1AP-MessageIdentifier                                        PRESENCE mandatory }|
        { ID id-SerialNumber                                CRITICALITY reject        TYPE S1AP-SerialNumber                                                PRESENCE mandatory }|
        { ID id-BroadcastCompletedAreaList        CRITICALITY ignore        TYPE S1AP-BroadcastCompletedAreaList                        PRESENCE optional        }|
        { ID id-CriticalityDiagnostics                CRITICALITY ignore        TYPE S1AP-CriticalityDiagnostics                                PRESENCE optional },
        ...
}


-- **************************************************************
--
-- eNB DIRECT INFORMATION TRANSFER ELEMENTARY PROCEDURE
--
-- **************************************************************


-- **************************************************************
--
-- eNB Direct Information Transfer
--
-- **************************************************************


S1AP-ENBDirectInformationTransfer ::= SEQUENCE {
        protocolIEs                        ProtocolIE-Container       {{ S1AP-ENBDirectInformationTransferIEs}},
        ...
}


S1AP-ENBDirectInformationTransferIEs S1AP-PROTOCOL-IES ::= {
        { ID id-Inter-SystemInformationTransferTypeEDT                CRITICALITY reject        TYPE S1AP-Inter-SystemInformationTransferType                        PRESENCE mandatory}  ,
        ...
}


S1AP-Inter-SystemInformationTransferType ::= CHOICE {
        rIMTransfer                S1AP-RIMTransfer,
        ...
}


-- **************************************************************
--
-- MME DIRECT INFORMATION TRANSFER ELEMENTARY PROCEDURE
--
-- **************************************************************


-- **************************************************************
--
-- MME Direct Information Transfer
--
-- **************************************************************


S1AP-MMEDirectInformationTransfer ::= SEQUENCE {
        protocolIEs                        ProtocolIE-Container       {{ S1AP-MMEDirectInformationTransferIEs}},
        ...
}


S1AP-MMEDirectInformationTransferIEs S1AP-PROTOCOL-IES ::= {
        { ID id-Inter-SystemInformationTransferTypeMDT                CRITICALITY reject        TYPE S1AP-Inter-SystemInformationTransferType                        PRESENCE mandatory}  ,
        ...
}
-- **************************************************************
--
-- eNB CONFIGURATION TRANSFER ELEMENTARY PROCEDURE
--
-- **************************************************************


-- **************************************************************
--
-- eNB Configuration Transfer
--
-- **************************************************************


S1AP-ENBConfigurationTransfer ::= SEQUENCE {
        protocolIEs                        ProtocolIE-Container       {{ S1AP-ENBConfigurationTransferIEs}},
        ...
}


S1AP-ENBConfigurationTransferIEs S1AP-PROTOCOL-IES ::= {
        { ID id-SONConfigurationTransferECT                CRITICALITY ignore        TYPE S1AP-SONConfigurationTransfer                                PRESENCE optional}  ,
        ...
}


-- **************************************************************
--
-- MME CONFIGURATION TRANSFER ELEMENTARY PROCEDURE
--
-- **************************************************************


-- **************************************************************
--
-- MME Configuration Transfer
--
-- **************************************************************


S1AP-MMEConfigurationTransfer ::= SEQUENCE {
        protocolIEs                        ProtocolIE-Container       {{ S1AP-MMEConfigurationTransferIEs}},
        ...
}


S1AP-MMEConfigurationTransferIEs S1AP-PROTOCOL-IES ::= {
        { ID id-SONConfigurationTransferMCT                CRITICALITY ignore        TYPE S1AP-SONConfigurationTransfer                                PRESENCE optional}  ,
        ...
}


-- **************************************************************
--
-- PRIVATE MESSAGE ELEMENTARY PROCEDURE
--
-- **************************************************************


-- **************************************************************
--
-- Private Message
--
-- **************************************************************


S1AP-PrivateMessage ::= SEQUENCE {
        privateIEs                        PrivateIE-Container       {{PrivateMessageIEs}},
        ...
}


PrivateMessageIEs S1AP-PRIVATE-IES ::= {
        ...
}


-- **************************************************************
--
-- Kill Request
--
-- **************************************************************




S1AP-KillRequest ::= SEQUENCE {
        protocolIEs                        ProtocolIE-Container       { {S1AP-KillRequestIEs} },
        ...
}


S1AP-KillRequestIEs S1AP-PROTOCOL-IES ::= {        
        { ID id-MessageIdentifier                        CRITICALITY reject        TYPE S1AP-MessageIdentifier                PRESENCE mandatory }|
        { ID id-SerialNumber                                CRITICALITY reject        TYPE S1AP-SerialNumber                        PRESENCE mandatory }|
        { ID id-WarningAreaList                                CRITICALITY ignore        TYPE S1AP-WarningAreaList                PRESENCE optional },
        ...
}


-- **************************************************************
--
-- Kill Response
--
-- **************************************************************


S1AP-KillResponse ::= SEQUENCE {
        protocolIEs                        ProtocolIE-Container                { {S1AP-KillResponseIEs} },
        ...
}


S1AP-KillResponseIEs S1AP-PROTOCOL-IES ::= {
        { ID id-MessageIdentifier                        CRITICALITY reject        TYPE S1AP-MessageIdentifier                                PRESENCE mandatory }|
        { ID id-SerialNumber                                CRITICALITY reject        TYPE S1AP-SerialNumber                                        PRESENCE mandatory }|
        { ID id-BroadcastCancelledAreaList        CRITICALITY ignore        TYPE S1AP-BroadcastCancelledAreaList                PRESENCE optional }|
        { ID id-CriticalityDiagnostics                CRITICALITY ignore        TYPE S1AP-CriticalityDiagnostics                        PRESENCE optional },
        ...
}


-- **************************************************************
--
-- LPPA TRANSPORT ELEMENTARY PROCEDURES
--
-- **************************************************************


-- **************************************************************
--
-- DOWNLINK UE ASSOCIATED LPPA TRANSPORT
--
-- **************************************************************


S1AP-DownlinkUEAssociatedLPPaTransport ::= SEQUENCE {
        protocolIEs                        ProtocolIE-Container       {{S1AP-DownlinkUEAssociatedLPPaTransport-IEs}},
        ...
}


S1AP-DownlinkUEAssociatedLPPaTransport-IEs S1AP-PROTOCOL-IES ::= {
        { ID id-MME-UE-S1AP-ID                        CRITICALITY reject        TYPE S1AP-MME-UE-S1AP-ID                                PRESENCE mandatory } |
        { ID id-eNB-UE-S1AP-ID                        CRITICALITY reject        TYPE S1AP-ENB-UE-S1AP-ID                                PRESENCE mandatory } |
        { ID id-Routing-ID                                CRITICALITY reject        TYPE S1AP-Routing-ID                                        PRESENCE mandatory } |
        { ID id-LPPa-PDU                            CRITICALITY reject        TYPE S1AP-LPPa-PDU                                   PRESENCE mandatory } ,
        ...
}


-- **************************************************************
--
-- UPLINK UE ASSOCIATED LPPA TRANSPORT
--
-- **************************************************************


S1AP-UplinkUEAssociatedLPPaTransport ::= SEQUENCE {
        protocolIEs                        ProtocolIE-Container       {{S1AP-UplinkUEAssociatedLPPaTransport-IEs}},
        ...
}


S1AP-UplinkUEAssociatedLPPaTransport-IEs S1AP-PROTOCOL-IES ::= {
        { ID id-MME-UE-S1AP-ID                        CRITICALITY reject        TYPE S1AP-MME-UE-S1AP-ID                                PRESENCE mandatory} |
        { ID id-eNB-UE-S1AP-ID                        CRITICALITY reject        TYPE S1AP-ENB-UE-S1AP-ID                                PRESENCE mandatory} |
        { ID id-Routing-ID                                CRITICALITY reject        TYPE S1AP-Routing-ID                                        PRESENCE mandatory} |
        { ID id-LPPa-PDU                            CRITICALITY reject        TYPE S1AP-LPPa-PDU                                   PRESENCE mandatory} ,
        ...
}


-- **************************************************************
--
-- DOWNLINK NON UE ASSOCIATED LPPA TRANSPORT
--
-- **************************************************************


S1AP-DownlinkNonUEAssociatedLPPaTransport ::= SEQUENCE {
        protocolIEs                        ProtocolIE-Container       {{S1AP-DownlinkNonUEAssociatedLPPaTransport-IEs}},
        ...
}


S1AP-DownlinkNonUEAssociatedLPPaTransport-IEs S1AP-PROTOCOL-IES ::= {
        { ID id-Routing-ID                            CRITICALITY reject        TYPE S1AP-Routing-ID                                    PRESENCE mandatory} | 
        { ID id-LPPa-PDU                            CRITICALITY reject        TYPE S1AP-LPPa-PDU                                   PRESENCE mandatory} ,
        ...
}


-- **************************************************************
--
-- UPLINK NON UE ASSOCIATED LPPA TRANSPORT
--
-- **************************************************************


S1AP-UplinkNonUEAssociatedLPPaTransport ::= SEQUENCE {
        protocolIEs                ProtocolIE-Container       {{S1AP-UplinkNonUEAssociatedLPPaTransport-IEs}},
        ...
}


S1AP-UplinkNonUEAssociatedLPPaTransport-IEs S1AP-PROTOCOL-IES ::= {
        { ID id-Routing-ID                            CRITICALITY reject        TYPE S1AP-Routing-ID                                        PRESENCE mandatory} | 
        { ID id-LPPa-PDU                            CRITICALITY reject        TYPE S1AP-LPPa-PDU                                   PRESENCE mandatory} ,
        ...
}


END




-- **************************************************************
--
-- Information Element Definitions
--
-- **************************************************************


S1AP-IEs { 
itu-t (0) identified-organization (4) etsi (0) mobileDomain (0) 
eps-Access (21) modules (3) s1ap (1) version1 (1) s1ap-IEs (2) }


DEFINITIONS AUTOMATIC TAGS ::= 


BEGIN


IMPORTS
        S1AP-Presence
FROM S1AP-CommonDataTypes

        id-E-RABInformationListItem,
        id-E-RABItem,
        id-Bearers-SubjectToStatusTransfer-Item, 
        id-Time-Synchronization-Info,
        id-x2TNLConfigurationInfo,
        id-eNBX2ExtendedTransportLayerAddresses,
        id-MDTConfiguration,
        s1ap-maxNrOfCSGs,
        s1ap-maxNrOfE-RABs,
        s1ap-maxNrOfErrors,
        s1ap-maxnoofBPLMNs,
        s1ap-maxnoofPLMNsPerMME,
        s1ap-maxnoofTACs,
        s1ap-maxnoofEPLMNs,
        s1ap-maxnoofEPLMNsPlusOne,
        s1ap-maxnoofForbLACs,
        s1ap-maxnoofForbTACs,
        s1ap-maxnoofCells,
        s1ap-maxnoofCellID,
        s1ap-maxnoofEmergencyAreaID,
        s1ap-maxnoofTAIforWarning,
        s1ap-maxnoofCellinTAI,
        s1ap-maxnoofCellinEAI,
        s1ap-maxnoofeNBX2TLAs,
        s1ap-maxnoofeNBX2ExtTLAs,
        s1ap-maxnoofeNBX2GTPTLAs,
        s1ap-maxnoofRATs,
        s1ap-maxnoofGroupIDs,
        s1ap-maxnoofMMECs,
        s1ap-maxnoofTAforMDT,
        s1ap-maxnoofCellIDforMDT






FROM S1AP-Constants


        S1AP-Criticality,
        S1AP-ProcedureCode,
        S1AP-ProtocolIE-ID,
        S1AP-TriggeringMessage
FROM S1AP-CommonDataTypes


        ProtocolExtensionContainer{},
        S1AP-PROTOCOL-EXTENSION,
        ProtocolIE-SingleContainer{},
        S1AP-PROTOCOL-IES


FROM S1AP-Containers

        S1ap-IE

FROM S1AP-PDU;


-- A


S1AP-AreaScopeOfMDT ::= CHOICE {        
        cellBased                                        S1AP-CellBasedMDT,
        tABased                                                S1AP-TABasedMDT,
        pLMNWide                                        NULL,
        ...
}


S1AP-AllocationAndRetentionPriority ::= SEQUENCE {
        priorityLevel                                S1AP-PriorityLevel,
        pre-emptionCapability                S1AP-Pre-emptionCapability,
        pre-emptionVulnerability        S1AP-Pre-emptionVulnerability,
        iE-Extensions                                ProtocolExtensionContainer { {S1AP-AllocationAndRetentionPriority-ExtIEs} } OPTIONAL,
        ...
}


S1AP-AllocationAndRetentionPriority-ExtIEs S1AP-PROTOCOL-EXTENSION ::= {
        ...
}




-- B


S1AP-Bearers-SubjectToStatusTransferList ::= SEQUENCE (SIZE(1.. s1ap-maxNrOfE-RABs)) OF ProtocolIE-SingleContainer { { S1AP-Bearers-SubjectToStatusTransfer-ItemIEs } }


S1AP-Bearers-SubjectToStatusTransfer-ItemIEs S1AP-PROTOCOL-IES ::= {
        { ID id-Bearers-SubjectToStatusTransfer-Item        CRITICALITY ignore        TYPE S1AP-Bearers-SubjectToStatusTransfer-Item         PRESENCE mandatory        },
        ...
}


S1AP-Bearers-SubjectToStatusTransfer-Item ::= SEQUENCE {
        e-RAB-ID                                                                S1AP-E-RAB-ID,
        uL-S1AP-COUNTvalue                                                        S1AP-COUNTvalue,
        dL-S1AP-COUNTvalue                                                        S1AP-COUNTvalue,
        receiveStatusofULPDCPSDUs                                S1AP-ReceiveStatusofULPDCPSDUs                        OPTIONAL,
        iE-Extensions                                                        ProtocolExtensionContainer { {S1AP-Bearers-SubjectToStatusTransfer-ItemExtIEs} } OPTIONAL,
        ...
}


S1AP-Bearers-SubjectToStatusTransfer-ItemExtIEs S1AP-PROTOCOL-EXTENSION ::= {
        ...
}


S1AP-BitRate        ::= INTEGER (0..10000000000) 


S1AP-BPLMNs ::= SEQUENCE (SIZE(1.. s1ap-maxnoofBPLMNs)) OF S1AP-PLMNidentity


S1AP-BroadcastCancelledAreaList ::= CHOICE {
        cellID-Cancelled                                S1AP-CellID-Cancelled,
        tAI-Cancelled                                        S1AP-TAI-Cancelled,
        emergencyAreaID-Cancelled                S1AP-EmergencyAreaID-Cancelled,
        ...
}


S1AP-BroadcastCompletedAreaList ::= CHOICE {
        cellID-Broadcast                                S1AP-CellID-Broadcast,
        tAI-Broadcast                                        S1AP-TAI-Broadcast,
        emergencyAreaID-Broadcast                S1AP-EmergencyAreaID-Broadcast,
        ...
}




-- C


S1AP-CancelledCellinEAI ::= SEQUENCE (SIZE(1..s1ap-maxnoofCellinEAI)) OF S1AP-CancelledCellinEAI-Item


S1AP-CancelledCellinEAI-Item ::= SEQUENCE {
        eCGI                                        S1AP-EUTRAN-CGI,
        numberOfBroadcasts                S1AP-NumberOfBroadcasts,
        iE-Extensions                        ProtocolExtensionContainer { {S1AP-CancelledCellinEAI-Item-ExtIEs} } OPTIONAL,
        ...
}


S1AP-CancelledCellinEAI-Item-ExtIEs S1AP-PROTOCOL-EXTENSION ::= {
        ...
}


S1AP-CancelledCellinTAI ::= SEQUENCE (SIZE(1..s1ap-maxnoofCellinTAI)) OF S1AP-CancelledCellinTAI-Item


S1AP-CancelledCellinTAI-Item ::= SEQUENCE{
        eCGI                                S1AP-EUTRAN-CGI,
        numberOfBroadcasts        S1AP-NumberOfBroadcasts,
        iE-Extensions                ProtocolExtensionContainer { {S1AP-CancelledCellinTAI-Item-ExtIEs} } OPTIONAL,
        ...
}


S1AP-CancelledCellinTAI-Item-ExtIEs S1AP-PROTOCOL-EXTENSION ::= {
        ...
}


S1AP-Cause ::= CHOICE {
        radioNetwork                S1AP-CauseRadioNetwork,
        transport                        S1AP-CauseTransport,
        nas                                        S1AP-CauseNas,
        protocol                        S1AP-CauseProtocol,
        misc                                S1AP-CauseMisc,
        ...
}


S1AP-CauseMisc ::= ENUMERATED {
        control-processing-overload,
        not-enough-user-plane-processing-resources,
        hardware-failure,
        om-intervention,
        unspecified,
        unknown-PLMN,
...
}


S1AP-CauseProtocol ::= ENUMERATED {
        transfer-syntax-error,
        abstract-syntax-error-reject,
        abstract-syntax-error-ignore-and-notify,
        message-not-compatible-with-receiver-state,
        semantic-error,
        abstract-syntax-error-falsely-constructed-message,
        unspecified,
        ...
}


S1AP-CauseRadioNetwork ::= ENUMERATED {
        unspecified,
        tx2relocoverall-expiry,
        successful-handover,
        release-due-to-eutran-generated-reason,
        handover-cancelled,        
        partial-handover,        
        ho-failure-in-target-EPC-eNB-or-target-system,
        ho-target-not-allowed,
        tS1relocoverall-expiry,
        tS1relocprep-expiry,
        cell-not-available,
        unknown-targetID,
        no-radio-resources-available-in-target-cell,
        unknown-mme-ue-s1ap-id,
        unknown-enb-ue-s1ap-id,
        unknown-pair-ue-s1ap-id,
        handover-desirable-for-radio-reason,
        time-critical-handover,
        resource-optimisation-handover,
        reduce-load-in-serving-cell,
        user-inactivity,
        radio-connection-with-ue-lost,
        load-balancing-tau-required,
        cs-fallback-triggered,
        ue-not-available-for-ps-service,
        radio-resources-not-available,
        failure-in-radio-interface-procedure,
        invalid-qos-combination,
        interrat-redirection,
        interaction-with-other-procedure,
        unknown-S1AP-E-RAB-ID,
        multiple-S1AP-E-RAB-ID-instances,
        encryption-and-or-integrity-protection-algorithms-not-supported,
        s1-intra-system-handover-triggered,
        s1-inter-system-handover-triggered,
        x2-handover-triggered,
        ...,
        redirection-towards-1xRTT,
        not-supported-S1AP-QCI-value,
        invalid-CSG-Id


}


S1AP-CauseTransport ::= ENUMERATED {
        transport-resource-unavailable,
        unspecified,
        ...
}


S1AP-CauseNas ::= ENUMERATED {
        normal-release,
        authentication-failure,
        detach,
        unspecified,
        ...,
        csg-subscription-expiry
}


S1AP-CellAccessMode ::= ENUMERATED {
        hybrid, 
        ...
}


S1AP-CellIdentity                        ::= BIT STRING (SIZE (28))


S1AP-CellID-Broadcast ::= SEQUENCE (SIZE(1..s1ap-maxnoofCellID)) OF S1AP-CellID-Broadcast-Item


S1AP-CellID-Broadcast-Item ::= SEQUENCE {
        eCGI                                S1AP-EUTRAN-CGI,
        iE-Extensions                ProtocolExtensionContainer { {S1AP-CellID-Broadcast-Item-ExtIEs} } OPTIONAL,
        ...
}


S1AP-CellID-Broadcast-Item-ExtIEs S1AP-PROTOCOL-EXTENSION ::= {
        ...
}


S1AP-CellID-Cancelled::= SEQUENCE (SIZE(1..s1ap-maxnoofCellID)) OF S1AP-CellID-Cancelled-Item


S1AP-CellID-Cancelled-Item ::= SEQUENCE {
        eCGI                                S1AP-EUTRAN-CGI,
        numberOfBroadcasts        S1AP-NumberOfBroadcasts,
        iE-Extensions                ProtocolExtensionContainer { {S1AP-CellID-Cancelled-Item-ExtIEs} } OPTIONAL,
        ...
}


S1AP-CellID-Cancelled-Item-ExtIEs S1AP-PROTOCOL-EXTENSION ::= {
        ...
}


S1AP-CellBasedMDT::= SEQUENCE {
        cellIdListforMDT        S1AP-CellIdListforMDT,
        iE-Extensions                ProtocolExtensionContainer { {S1AP-CellBasedMDT-ExtIEs} } OPTIONAL,
        ...
}


S1AP-CellBasedMDT-ExtIEs S1AP-PROTOCOL-EXTENSION ::= {
        ...
}


S1AP-CellIdListforMDT ::= SEQUENCE (SIZE(1..s1ap-maxnoofCellIDforMDT)) OF S1AP-EUTRAN-CGI


S1AP-Cdma2000PDU        ::= OCTET STRING


S1AP-Cdma2000RATType ::= ENUMERATED {
        hRPD,
        onexRTT,
        ...
}


S1AP-Cdma2000SectorID ::= OCTET STRING


S1AP-Cdma2000HOStatus ::= ENUMERATED {
        hOSuccess,
        hOFailure,
        ...
}


S1AP-Cdma2000HORequiredIndication ::= ENUMERATED {
        true,
        ...
}


S1AP-Cdma2000OneXSRVCCInfo ::= SEQUENCE {
        cdma2000OneXMEID                        S1AP-Cdma2000OneXMEID,
        cdma2000OneXMSI                                S1AP-Cdma2000OneXMSI,
        cdma2000OneXPilot                        S1AP-Cdma2000OneXPilot,
        iE-Extensions                                ProtocolExtensionContainer { {S1AP-Cdma2000OneXSRVCCInfo-ExtIEs} } OPTIONAL,
        ...
}


S1AP-Cdma2000OneXSRVCCInfo-ExtIEs S1AP-PROTOCOL-EXTENSION ::= {
        ...
}


S1AP-Cdma2000OneXMEID ::= OCTET STRING


S1AP-Cdma2000OneXMSI ::= OCTET STRING


S1AP-Cdma2000OneXPilot ::= OCTET STRING


S1AP-Cdma2000OneXRAND ::= OCTET STRING




S1AP-Cell-Size ::= ENUMERATED {verysmall, small, medium, large, ...}


S1AP-CellType ::= SEQUENCE {
        cell-Size                                S1AP-Cell-Size,
        iE-Extensions                        ProtocolExtensionContainer { { S1AP-CellType-ExtIEs}}        OPTIONAL,
        ...
}


S1AP-CellType-ExtIEs S1AP-PROTOCOL-EXTENSION ::= {
        ...
}


S1AP-CGI ::= SEQUENCE {
        pLMNidentity                                S1AP-PLMNidentity,
        lAC                                S1AP-LAC,
        cI                                S1AP-CI,
        rAC                                S1AP-RAC                                                OPTIONAL,
        iE-Extensions        ProtocolExtensionContainer { {S1AP-CGI-ExtIEs} } OPTIONAL,
        ...
        }


S1AP-CGI-ExtIEs S1AP-PROTOCOL-EXTENSION ::= {
        ...
}


S1AP-CI                                        ::= OCTET STRING (SIZE (2))


S1AP-CNDomain ::= ENUMERATED {
        ps, 
        cs 
}


S1AP-ConcurrentWarningMessageIndicator ::= ENUMERATED {
        true
}


S1AP-Correlation-ID                ::= OCTET STRING (SIZE (4))


S1AP-CSFallbackIndicator ::= ENUMERATED { 
        cs-fallback-required,
        ...,
        cs-fallback-high-priority 
}


S1AP-CSG-Id                ::= BIT STRING (SIZE (27))




S1AP-CSG-IdList ::= SEQUENCE (SIZE (1..s1ap-maxNrOfCSGs)) OF S1AP-CSG-IdList-Item


S1AP-CSG-IdList-Item ::= SEQUENCE {
        cSG-Id                        S1AP-CSG-Id,
        iE-Extensions        ProtocolExtensionContainer { {S1AP-CSG-IdList-Item-ExtIEs} } OPTIONAL,
        ...
}


S1AP-CSG-IdList-Item-ExtIEs S1AP-PROTOCOL-EXTENSION ::= {
        ...
}


S1AP-CSGMembershipStatus ::= ENUMERATED { 
        member, 
        not-member
}




S1AP-COUNTvalue ::= SEQUENCE {
        pDCP-SN                        S1AP-PDCP-SN,
        hFN                                S1AP-HFN,
        iE-Extensions        ProtocolExtensionContainer { {S1AP-COUNTvalue-ExtIEs} } OPTIONAL,
        ...
}
S1AP-COUNTvalue-ExtIEs S1AP-PROTOCOL-EXTENSION ::= {
        ...
}


S1AP-CriticalityDiagnostics ::= SEQUENCE {
        procedureCode                                        S1AP-ProcedureCode                                        OPTIONAL,
        triggeringMessage                                S1AP-TriggeringMessage                                OPTIONAL,
        procedureCriticality                        S1AP-Criticality                                                OPTIONAL,
        iEsCriticalityDiagnostics                S1AP-CriticalityDiagnostics-IE-List         OPTIONAL,
        iE-Extensions                                        ProtocolExtensionContainer {{S1AP-CriticalityDiagnostics-ExtIEs}} OPTIONAL,
        ...
}


S1AP-CriticalityDiagnostics-ExtIEs S1AP-PROTOCOL-EXTENSION ::= {
        ...
}


S1AP-CriticalityDiagnostics-IE-List ::= SEQUENCE (SIZE (1..s1ap-maxNrOfErrors)) OF S1AP-CriticalityDiagnostics-IE-Item


S1AP-CriticalityDiagnostics-IE-Item ::=         SEQUENCE {
        iECriticality                        S1AP-Criticality,
        iE-ID                                        S1AP-ProtocolIE-ID,
        typeOfError                         S1AP-TypeOfError,
        iE-Extensions                        ProtocolExtensionContainer {{S1AP-CriticalityDiagnostics-IE-Item-ExtIEs}} OPTIONAL,
        ...
}


S1AP-CriticalityDiagnostics-IE-Item-ExtIEs S1AP-PROTOCOL-EXTENSION ::= {
        ...
}




-- D


S1AP-DataCodingScheme ::= BIT STRING (SIZE (8))


S1AP-DL-Forwarding ::= ENUMERATED {
        dL-Forwarding-proposed,
        ...
}


S1AP-Direct-Forwarding-Path-Availability ::= ENUMERATED {
        directPathAvailable,
        ...
}


S1AP-Data-Forwarding-Not-Possible ::= ENUMERATED {
        data-Forwarding-not-Possible,
        ...
}


-- E


S1AP-ECGIList ::= SEQUENCE (SIZE(1..s1ap-maxnoofCellID)) OF S1AP-EUTRAN-CGI


S1AP-EmergencyAreaIDList ::= SEQUENCE (SIZE(1..s1ap-maxnoofEmergencyAreaID)) OF S1AP-EmergencyAreaID


S1AP-EmergencyAreaID ::= OCTET STRING (SIZE (3))


S1AP-EmergencyAreaID-Broadcast ::= SEQUENCE (SIZE(1..s1ap-maxnoofEmergencyAreaID)) OF S1AP-EmergencyAreaID-Broadcast-Item


S1AP-EmergencyAreaID-Broadcast-Item ::= SEQUENCE {
        emergencyAreaID                        S1AP-EmergencyAreaID,
        completedCellinEAI                S1AP-CompletedCellinEAI,
        iE-Extensions                        ProtocolExtensionContainer { {S1AP-EmergencyAreaID-Broadcast-Item-ExtIEs} } OPTIONAL,
        ...
}


S1AP-EmergencyAreaID-Broadcast-Item-ExtIEs S1AP-PROTOCOL-EXTENSION ::= {
        ...
}


S1AP-EmergencyAreaID-Cancelled ::= SEQUENCE (SIZE(1..s1ap-maxnoofEmergencyAreaID)) OF S1AP-EmergencyAreaID-Cancelled-Item


S1AP-EmergencyAreaID-Cancelled-Item ::= SEQUENCE {
        emergencyAreaID                        S1AP-EmergencyAreaID,
        cancelledCellinEAI                S1AP-CancelledCellinEAI,
        iE-Extensions                        ProtocolExtensionContainer { {S1AP-EmergencyAreaID-Cancelled-Item-ExtIEs} } OPTIONAL,
        ...
}


S1AP-EmergencyAreaID-Cancelled-Item-ExtIEs S1AP-PROTOCOL-EXTENSION ::= {
        ...
}


S1AP-CompletedCellinEAI ::= SEQUENCE (SIZE(1..s1ap-maxnoofCellinEAI)) OF S1AP-CompletedCellinEAI-Item


S1AP-CompletedCellinEAI-Item ::= SEQUENCE {
        eCGI                                        S1AP-EUTRAN-CGI,
        iE-Extensions                        ProtocolExtensionContainer { {S1AP-CompletedCellinEAI-Item-ExtIEs} } OPTIONAL,
        ...
}


S1AP-CompletedCellinEAI-Item-ExtIEs S1AP-PROTOCOL-EXTENSION ::= {
        ...
}


S1AP-ENB-ID ::= CHOICE {
        macroENB-ID                        BIT STRING (SIZE(20)),
        homeENB-ID                        BIT STRING (SIZE(28)),
        ...
}


S1AP-GERAN-Cell-ID ::= SEQUENCE {
        lAI                                S1AP-LAI,
    rAC                                S1AP-RAC, 
        cI                                S1AP-CI,
        iE-Extensions                        ProtocolExtensionContainer { { S1AP-GERAN-Cell-ID-ExtIEs} } OPTIONAL,
        ...
}


S1AP-GERAN-Cell-ID-ExtIEs S1AP-PROTOCOL-EXTENSION ::= {
        ...
}


S1AP-Global-ENB-ID ::= SEQUENCE {
        pLMNidentity                        S1AP-PLMNidentity,
        eNB-ID                                        S1AP-ENB-ID,
        iE-Extensions                        ProtocolExtensionContainer { {S1AP-GlobalENB-ID-ExtIEs} } OPTIONAL,
        ...
}


S1AP-GlobalENB-ID-ExtIEs S1AP-PROTOCOL-EXTENSION ::= {
        ...
}


S1AP-GUMMEIList::= SEQUENCE (SIZE (1.. s1ap-maxnoofMMECs)) OF S1AP-GUMMEI


S1AP-ENB-StatusTransfer-TransparentContainer                ::= SEQUENCE {
        bearers-SubjectToStatusTransferList                S1AP-Bearers-SubjectToStatusTransferList,
        iE-Extensions                        ProtocolExtensionContainer { {S1AP-ENB-StatusTransfer-TransparentContainer-ExtIEs} } OPTIONAL,
        ...
}


S1AP-ENB-StatusTransfer-TransparentContainer-ExtIEs S1AP-PROTOCOL-EXTENSION ::= {
        ...
}


S1AP-ENB-UE-S1AP-ID                                ::= INTEGER (0..16777215)


S1AP-ENBname ::= PrintableString (SIZE (1..150,...))


S1AP-ENBX2TLAs ::= SEQUENCE (SIZE(1.. s1ap-maxnoofeNBX2TLAs)) OF S1AP-TransportLayerAddress


S1AP-EncryptionAlgorithms ::= BIT STRING (SIZE (16,...))


S1AP-EPLMNs ::= SEQUENCE (SIZE(1..s1ap-maxnoofEPLMNs)) OF S1AP-PLMNidentity
S1AP-EventType        ::= ENUMERATED {
        direct,
        change-of-serve-cell,
        stop-change-of-serve-cell,
        ...
}


S1AP-E-RAB-ID                ::= INTEGER (0..15, ...)


S1AP-E-RABInformationList        ::= SEQUENCE (SIZE (1.. s1ap-maxNrOfE-RABs)) OF ProtocolIE-SingleContainer { { S1AP-E-RABInformationListIEs } }


S1AP-E-RABInformationListIEs S1AP-PROTOCOL-IES ::= {
        { ID id-E-RABInformationListItem                        CRITICALITY ignore        TYPE S1AP-E-RABInformationListItem                        PRESENCE mandatory        },
        ...
}


S1AP-E-RABInformationListItem ::= SEQUENCE {
        e-RAB-ID                                                S1AP-E-RAB-ID,
        dL-Forwarding                                        S1AP-DL-Forwarding                OPTIONAL,
        iE-Extensions                                        ProtocolExtensionContainer { {S1AP-E-RABInformationListItem-ExtIEs} }                        OPTIONAL,
        ...
}


S1AP-E-RABInformationListItem-ExtIEs S1AP-PROTOCOL-EXTENSION ::= {
        ...
}


S1AP-E-RABList ::= SEQUENCE (SIZE(1.. s1ap-maxNrOfE-RABs)) OF ProtocolIE-SingleContainer { {S1AP-E-RABItemIEs} }


S1AP-E-RABItemIEs         S1AP-PROTOCOL-IES ::= {
        { ID id-E-RABItem         CRITICALITY ignore         TYPE S1AP-E-RABItem         PRESENCE mandatory },
        ...
}


S1AP-E-RABItem ::= SEQUENCE {
        e-RAB-ID                                        S1AP-E-RAB-ID,
        cause                                                S1AP-Cause,
        iE-Extensions                                ProtocolExtensionContainer { {S1AP-E-RABItem-ExtIEs} } OPTIONAL,
        ...
}


S1AP-E-RABItem-ExtIEs S1AP-PROTOCOL-EXTENSION ::= {
        ...
}




S1AP-E-RABLevelQoSParameters ::= SEQUENCE {
        qCI                        S1AP-QCI,
        allocationRetentionPriority                        S1AP-AllocationAndRetentionPriority,
        gbrQosInformation                                        S1AP-GBR-QosInformation                        OPTIONAL,
        iE-Extensions                                                ProtocolExtensionContainer { {S1AP-E-RABQoSParameters-ExtIEs} } OPTIONAL,
        ...
}


S1AP-E-RABQoSParameters-ExtIEs S1AP-PROTOCOL-EXTENSION ::= {
        ...
}




S1AP-EUTRAN-CGI ::= SEQUENCE {
        pLMNidentity                        S1AP-PLMNidentity,
        cell-ID                                        S1AP-CellIdentity,
        iE-Extensions                        ProtocolExtensionContainer { {S1AP-EUTRAN-CGI-ExtIEs} } OPTIONAL,
        ...
}


S1AP-EUTRAN-CGI-ExtIEs S1AP-PROTOCOL-EXTENSION ::= {
        ...
}


S1AP-EUTRANRoundTripDelayEstimationInfo ::= INTEGER (0..2047)


S1AP-ExtendedRNC-ID                                        ::= INTEGER (4096..65535)


S1AP-ExtendedRepetitionPeriod ::= INTEGER (4096..131071)


-- F


S1AP-ForbiddenInterRATs ::= ENUMERATED {
        all,
        geran,
        utran,
        cdma2000,
        ...,
        geranandutran,
        cdma2000andutran


}


S1AP-ForbiddenTAs ::= SEQUENCE (SIZE(1.. s1ap-maxnoofEPLMNsPlusOne)) OF S1AP-ForbiddenTAs-Item


S1AP-ForbiddenTAs-Item ::= SEQUENCE {
        pLMN-Identity                S1AP-PLMNidentity,
        forbiddenTACs                S1AP-ForbiddenTACs,
        iE-Extensions                ProtocolExtensionContainer { {S1AP-ForbiddenTAs-Item-ExtIEs} } OPTIONAL,
        ...
}


S1AP-ForbiddenTAs-Item-ExtIEs S1AP-PROTOCOL-EXTENSION ::= {
        ...
}


S1AP-ForbiddenTACs ::= SEQUENCE (SIZE(1..s1ap-maxnoofForbTACs)) OF S1AP-TAC


S1AP-ForbiddenLAs ::= SEQUENCE (SIZE(1..s1ap-maxnoofEPLMNsPlusOne)) OF S1AP-ForbiddenLAs-Item


S1AP-ForbiddenLAs-Item ::= SEQUENCE {
        pLMN-Identity                S1AP-PLMNidentity,
        forbiddenLACs                S1AP-ForbiddenLACs,
        iE-Extensions                ProtocolExtensionContainer { {S1AP-ForbiddenLAs-Item-ExtIEs} } OPTIONAL,
        ...
}


S1AP-ForbiddenLAs-Item-ExtIEs S1AP-PROTOCOL-EXTENSION ::= {
        ...
}


S1AP-ForbiddenLACs ::= SEQUENCE (SIZE(1..s1ap-maxnoofForbLACs)) OF S1AP-LAC


-- G


S1AP-GBR-QosInformation ::= SEQUENCE {
        e-RAB-MaximumBitrateDL                        S1AP-BitRate,
        e-RAB-MaximumBitrateUL                        S1AP-BitRate,
        e-RAB-GuaranteedBitrateDL                S1AP-BitRate,
        e-RAB-GuaranteedBitrateUL                S1AP-BitRate,
        iE-Extensions                                        ProtocolExtensionContainer { { S1AP-GBR-QosInformation-ExtIEs} } OPTIONAL,
        ...
}


S1AP-GBR-QosInformation-ExtIEs S1AP-PROTOCOL-EXTENSION ::= {
        ...
}




S1AP-GTP-TEID                                        ::= OCTET STRING (SIZE (4))


S1AP-GUMMEI                        ::= SEQUENCE {
        pLMN-Identity                S1AP-PLMNidentity,
        mME-Group-ID                S1AP-MME-Group-ID,
        mME-Code                        S1AP-MME-Code,
        iE-Extensions                ProtocolExtensionContainer { {S1AP-GUMMEI-ExtIEs} } OPTIONAL,
        ...
}


S1AP-GUMMEI-ExtIEs S1AP-PROTOCOL-EXTENSION ::= {
        ...
}

S1AP-GUMMEIType ::= ENUMERATED {
	native,
	mapped,
	...
}

S1AP-GWContextReleaseIndication ::= ENUMERATED {
        true,
        ...
}


-- H


S1AP-HandoverRestrictionList ::= SEQUENCE {
        servingPLMN                                        S1AP-PLMNidentity,
        equivalentPLMNs                                S1AP-EPLMNs                                        OPTIONAL,
        forbiddenTAs                                S1AP-ForbiddenTAs                        OPTIONAL,
        forbiddenLAs                                S1AP-ForbiddenLAs                        OPTIONAL,
        forbiddenInterRATs                        S1AP-ForbiddenInterRATs                OPTIONAL, 
        iE-Extensions                                ProtocolExtensionContainer { {S1AP-HandoverRestrictionList-ExtIEs} }        OPTIONAL,
        ...
}


S1AP-HandoverRestrictionList-ExtIEs S1AP-PROTOCOL-EXTENSION ::= {
        ...
}


S1AP-HandoverType ::= ENUMERATED {
        intralte,
        ltetoutran,
        ltetogeran,
        utrantolte,
        gerantolte,
        ...
}


S1AP-HFN ::= INTEGER (0..1048575)


-- I


S1AP-ImmediateMDT ::= SEQUENCE { 
        measurementsToActivate                S1AP-MeasurementsToActivate,
        reportingTriggerMDT                        S1AP-ReportingTriggerMDT,
        thresholdeventA2                        S1AP-ThresholdEventA2                                OPTIONAL,
-- Included in case of event-triggered reporting for measurement M1
        periodicReportingMDT                S1AP-PeriodicReportingMDT                        OPTIONAL,
-- Included in case of periodic reporting
        iE-Extensions                                ProtocolExtensionContainer { { S1AP-ImmediateMDT-ExtIEs} } OPTIONAL,
        ...
}


S1AP-ImmediateMDT-ExtIEs S1AP-PROTOCOL-EXTENSION ::= {
        ...
}


S1AP-IMSI        ::=        OCTET STRING (SIZE (3..8))


S1AP-IntegrityProtectionAlgorithms ::= BIT STRING (SIZE (16,...))


S1AP-InterfacesToTrace ::= BIT STRING (SIZE (8))






-- J
-- K
-- L




S1AP-LAC        ::= OCTET STRING (SIZE (2))


S1AP-LAI ::= SEQUENCE {
        pLMNidentity                                S1AP-PLMNidentity,
        lAC                                S1AP-LAC,
        iE-Extensions                        ProtocolExtensionContainer { {S1AP-LAI-ExtIEs} } OPTIONAL,
        ...
}


S1AP-LAI-ExtIEs S1AP-PROTOCOL-EXTENSION ::= {
        ...
}


S1AP-LastVisitedCell-Item ::= CHOICE {
        e-UTRAN-Cell                                        S1AP-LastVisitedEUTRANCellInformation,
        uTRAN-Cell                                                S1AP-LastVisitedUTRANCellInformation,
        gERAN-Cell                                                S1AP-LastVisitedGERANCellInformation,
        ...
}
S1AP-LastVisitedEUTRANCellInformation ::= SEQUENCE {
        global-Cell-ID                                        S1AP-EUTRAN-CGI,
        cellType                                                S1AP-CellType,
        time-UE-StayedInCell                        S1AP-Time-UE-StayedInCell,
        iE-Extensions                                        ProtocolExtensionContainer { { S1AP-LastVisitedEUTRANCellInformation-ExtIEs} } OPTIONAL,
        ...
}
S1AP-LastVisitedEUTRANCellInformation-ExtIEs S1AP-PROTOCOL-EXTENSION ::= {
        ...
}
S1AP-LastVisitedUTRANCellInformation        ::= OCTET STRING


S1AP-LastVisitedGERANCellInformation ::= CHOICE {
        undefined                                                NULL,
        ...
}


S1AP-L3-Information                                ::= OCTET STRING
-- This is a dummy IE used only as a reference to the actual definition in relevant specification.


S1AP-LPPa-PDU ::=  OCTET STRING


S1AP-LoggedMDT ::= SEQUENCE {
        loggingInterval                                S1AP-LoggingInterval,
        loggingDuration                                S1AP-LoggingDuration,
        iE-Extensions                                ProtocolExtensionContainer { {S1AP-LoggedMDT-ExtIEs} } OPTIONAL,
        ...
}


S1AP-LoggedMDT-ExtIEs        S1AP-PROTOCOL-EXTENSION ::= {
...
}


S1AP-LoggingInterval ::= ENUMERATED {ms128, ms256, ms512, ms1024, ms2048, ms3072, ms4096, ms6144}


S1AP-LoggingDuration ::= ENUMERATED {m10, m20, m40, m60, m90, m120}


-- M


S1AP-MDT-Activation         ::= ENUMERATED { 
        immediate-MDT-only,
        immediate-MDT-and-Trace,
        logged-MDT-only,
        ...
}


S1AP-MDT-Configuration ::= SEQUENCE {
        mdt-Activation                                S1AP-MDT-Activation,
        areaScopeOfMDT                                S1AP-AreaScopeOfMDT,
        mDTMode                                                S1AP-MDTMode,
        iE-Extensions                                ProtocolExtensionContainer { { S1AP-MDT-Configuration-ExtIEs} } OPTIONAL,
        ...
}
S1AP-MDT-Configuration-ExtIEs S1AP-PROTOCOL-EXTENSION ::= {
        ...
}


S1AP-ManagementBasedMDTAllowed ::= ENUMERATED {allowed, ...}


S1AP-PrivacyIndicator ::= ENUMERATED {
        immediate-MDT,
        logged-MDT,
        ...
}


S1AP-MDTMode ::= CHOICE {
        immediateMDT                                S1AP-ImmediateMDT,
        loggedMDT                                        S1AP-LoggedMDT,
        ...
}


S1AP-MeasurementsToActivate ::= BIT STRING (SIZE (8))


S1AP-MeasurementThresholdA2 ::= CHOICE { 
        threshold-RSRP                                S1AP-Threshold-RSRP,
        threshold-RSRQ                                S1AP-Threshold-RSRQ,
        ...
}


S1AP-MessageIdentifier        ::= BIT STRING (SIZE (16))


S1AP-MMEname ::= PrintableString (SIZE (1..150,...))


S1AP-MMERelaySupportIndicator ::= ENUMERATED {true, ...}


S1AP-MME-Group-ID        ::= OCTET STRING (SIZE (2))


S1AP-MME-Code                ::= OCTET STRING (SIZE (1))


S1AP-MME-UE-S1AP-ID        ::= INTEGER (0..4294967295)
S1AP-M-TMSI                        ::= OCTET STRING (SIZE (4))


S1AP-MSClassmark2        ::= OCTET STRING
S1AP-MSClassmark3        ::= OCTET STRING


-- N


S1AP-NAS-PDU ::=  OCTET STRING


S1AP-NASSecurityParametersfromE-UTRAN ::= OCTET STRING


S1AP-NASSecurityParameterstoE-UTRAN ::= OCTET STRING


S1AP-NumberofBroadcastRequest ::= INTEGER (0..65535)


S1AP-NumberOfBroadcasts ::= INTEGER (0..65535)


-- O
S1AP-OldBSS-ToNewBSS-Information                ::= OCTET STRING
-- This is a dummy IE used only as a reference to the actual definition in relevant specification.


S1AP-OverloadAction ::= ENUMERATED {
        reject-non-emergency-mo-dt,
        reject-rrc-cr-signalling,
        permit-emergency-sessions-and-mobile-terminated-services-only,
        ...,
        permit-high-priority-sessions-and-mobile-terminated-services-only,
        reject-delay-tolerant-access
}


S1AP-OverloadResponse ::= CHOICE {
        overloadAction                                        S1AP-OverloadAction,
        ...
}




-- P


S1AP-PagingDRX ::= ENUMERATED {
        v32,
        v64,
        v128,
        v256,
        ...
        }


S1AP-PagingPriority ::= ENUMERATED {
        priolevel1,
        priolevel2,
        priolevel3,
        priolevel4,
        priolevel5,
        priolevel6,
        priolevel7,
        priolevel8,
        ...
}


S1AP-PDCP-SN ::= INTEGER (0..4095) 


S1AP-PeriodicReportingMDT ::= SEQUENCE { 
        reportInterval                                S1AP-ReportIntervalMDT,
        reportAmount                                S1AP-ReportAmountMDT,
        iE-Extensions                                ProtocolExtensionContainer { { S1AP-PeriodicReportingMDT-ExtIEs} } OPTIONAL,
        ...
}


S1AP-PeriodicReportingMDT-ExtIEs S1AP-PROTOCOL-EXTENSION ::= {
        ...
}


S1AP-PLMNidentity                                 ::= S1AP-TBCD-STRING 


S1AP-Pre-emptionCapability ::= ENUMERATED {
        shall-not-trigger-pre-emption,
        may-trigger-pre-emption
}


S1AP-Pre-emptionVulnerability ::= ENUMERATED {
        not-pre-emptable,
        pre-emptable
}


S1AP-PriorityLevel                                ::= INTEGER { spare (0), highest (1), lowest (14), no-priority (15) } (0..15)


S1AP-PS-ServiceNotAvailable ::= ENUMERATED {
        ps-service-not-available,
        ...
}


-- Q


S1AP-QCI                                                ::= INTEGER (0..255)


-- R


S1AP-ReceiveStatusofULPDCPSDUs ::= BIT STRING (SIZE(4096))


S1AP-RelativeMMECapacity                                ::= INTEGER (0..255)


S1AP-RelayNode-Indicator ::= ENUMERATED {
        true,
        ...
}


S1AP-RAC                                        ::= OCTET STRING (SIZE (1))


S1AP-ReportAmountMDT ::= ENUMERATED{r1, r2, r4, r8, r16, r32, r64, rinfinity}


S1AP-ReportIntervalMDT ::= ENUMERATED {ms120, ms240, ms480, ms640, ms1024, ms2048, ms5120, ms10240, min1, min6, min12, min30, min60} 


S1AP-ReportingTriggerMDT ::= ENUMERATED{
        periodic,
        a2eventtriggered,
        ...
}


S1AP-RequestType        ::= SEQUENCE {
        eventType                                 S1AP-EventType,
        reportArea                                 S1AP-ReportArea,
        iE-Extensions                        ProtocolExtensionContainer { { S1AP-RequestType-ExtIEs} }        OPTIONAL,
        ...
}




S1AP-RequestType-ExtIEs S1AP-PROTOCOL-EXTENSION ::= {
        ...
}


S1AP-RIMTransfer ::= SEQUENCE {
        rIMInformation                        S1AP-RIMInformation,
        rIMRoutingAddress                S1AP-RIMRoutingAddress                OPTIONAL,
        iE-Extensions                        ProtocolExtensionContainer { { S1AP-RIMTransfer-ExtIEs} }                        OPTIONAL,
        ...
}


S1AP-RIMTransfer-ExtIEs S1AP-PROTOCOL-EXTENSION ::= {
        ...
}


S1AP-RIMInformation ::= OCTET STRING


S1AP-RIMRoutingAddress ::= CHOICE {
        gERAN-Cell-ID                        S1AP-GERAN-Cell-ID,
        ...,
        targetRNC-ID                        S1AP-TargetRNC-ID
}


S1AP-ReportArea ::= ENUMERATED {
        ecgi,
        ...
}


S1AP-RepetitionPeriod ::= INTEGER (0..4095)




S1AP-RNC-ID                                        ::= INTEGER (0..4095)


S1AP-RRC-Container        ::= OCTET STRING


S1AP-RRC-Establishment-Cause ::= ENUMERATED {
        emergency,
        highPriorityAccess,
        mt-Access,
        mo-Signalling,
        mo-Data,
        ...,
        delay-TolerantAccess
}


S1AP-Routing-ID                ::= INTEGER (0..255)


-- S




S1AP-SecurityKey        ::= BIT STRING (SIZE(256))






S1AP-SecurityContext ::= SEQUENCE {
        nextHopChainingCount                INTEGER (0..7),
        nextHopParameter                        S1AP-SecurityKey,
        iE-Extensions                                ProtocolExtensionContainer { { S1AP-SecurityContext-ExtIEs} } OPTIONAL,
        ...
}




S1AP-SecurityContext-ExtIEs S1AP-PROTOCOL-EXTENSION ::= {
        ...
}


S1AP-SerialNumber ::= BIT STRING (SIZE (16))


S1AP-SONInformation ::= CHOICE{
        sONInformationRequest                S1AP-SONInformationRequest,
        sONInformationReply                        S1AP-SONInformationReply,
        ...
}


S1AP-SONInformationRequest ::= ENUMERATED { 
        x2TNL-Configuration-Info,
        ...,
        time-Synchronization-Info}


S1AP-SONInformationReply ::= SEQUENCE {
        x2TNLConfigurationInfo                        S1AP-X2TNLConfigurationInfo                        OPTIONAL,
        iE-Extensions                                        ProtocolExtensionContainer {{S1AP-SONInformationReply-ExtIEs}} OPTIONAL,
        ...
}


S1AP-SONInformationReply-ExtIEs S1AP-PROTOCOL-EXTENSION ::= {
-- Extension for Release 9 to transfer Time synchronization information --
        {ID id-Time-Synchronization-Info        CRITICALITY ignore                EXTENSION S1AP-TimeSynchronizationInfo                PRESENCE optional},
        ...
}




S1AP-SONConfigurationTransfer ::= SEQUENCE {
        targeteNB-ID                                        S1AP-TargeteNB-ID,
        sourceeNB-ID                                        S1AP-SourceeNB-ID,
        sONInformation                                        S1AP-SONInformation,
        iE-Extensions                        ProtocolExtensionContainer { { S1AP-SONConfigurationTransfer-ExtIEs} }                        OPTIONAL,
...
}


S1AP-SONConfigurationTransfer-ExtIEs S1AP-PROTOCOL-EXTENSION ::= {
-- Extension for Release 10 to transfer the IP addresses of the eNB initiating the ANR action --
        {ID id-x2TNLConfigurationInfo        CRITICALITY ignore        EXTENSION S1AP-X2TNLConfigurationInfo        PRESENCE conditional
        -- This IE shall be present if the SON Information IE contains the SON Information Request IE and the SON Information Request IE is set to X2TNL Configuration Info -- },
        ...
}






S1AP-Source-ToTarget-TransparentContainer ::= OCTET STRING
-- This IE includes a transparent container from the source RAN node to the target RAN node. 
-- The octets of the OCTET STRING are encoded according to the specifications of the target system.


S1AP-SourceBSS-ToTargetBSS-TransparentContainer                ::= OCTET STRING
-- This is a dummy IE used only as a reference to the actual definition in relevant specification.


S1AP-SourceeNB-ID ::= SEQUENCE {
        global-S1AP-ENB-ID        S1AP-Global-ENB-ID,
        selected-S1AP-TAI        S1AP-TAI,
        iE-Extensions        ProtocolExtensionContainer { {S1AP-SourceeNB-ID-ExtIEs} } OPTIONAL
}


S1AP-SourceeNB-ID-ExtIEs S1AP-PROTOCOL-EXTENSION ::= {
        ...
}


S1AP-SRVCCOperationPossible ::= ENUMERATED {
        possible,
        ...
}


S1AP-SRVCCHOIndication ::= ENUMERATED {
        pSandCS,
        cSonly,
        ...
}


S1AP-SourceeNB-ToTargeteNB-TransparentContainer                ::= SEQUENCE {
        rRC-Container                                        S1AP-RRC-Container,
        e-RABInformationList                        S1AP-E-RABInformationList                OPTIONAL,
        targetCell-ID                                        S1AP-EUTRAN-CGI,
        subscriberProfileIDforRFP                S1AP-SubscriberProfileIDforRFP                OPTIONAL,
        uE-HistoryInformation                        S1AP-UE-HistoryInformation,
        iE-Extensions                        ProtocolExtensionContainer { {S1AP-SourceeNB-ToTargeteNB-TransparentContainer-ExtIEs} } OPTIONAL,
        ...
}


S1AP-SourceeNB-ToTargeteNB-TransparentContainer-ExtIEs S1AP-PROTOCOL-EXTENSION ::= {
        ...
}




S1AP-SourceRNC-ToTargetRNC-TransparentContainer                ::= OCTET STRING
-- This is a dummy IE used only as a reference to the actual definition in relevant specification.




S1AP-ServedGUMMEIs ::= SEQUENCE (SIZE (1.. s1ap-maxnoofRATs)) OF S1AP-ServedGUMMEIsItem


S1AP-ServedGUMMEIsItem ::= SEQUENCE {
        servedPLMNs                                S1AP-ServedPLMNs,
        servedGroupIDs                        S1AP-ServedGroupIDs,
        servedMMECs                                S1AP-ServedMMECs,
        iE-Extensions                        ProtocolExtensionContainer { {S1AP-ServedGUMMEIsItem-ExtIEs} }        OPTIONAL,
        ...
}


S1AP-ServedGUMMEIsItem-ExtIEs S1AP-PROTOCOL-EXTENSION ::= {
        ...
}


S1AP-ServedGroupIDs ::= SEQUENCE (SIZE(1.. s1ap-maxnoofGroupIDs)) OF S1AP-MME-Group-ID
S1AP-ServedMMECs ::= SEQUENCE (SIZE(1.. s1ap-maxnoofMMECs)) OF S1AP-MME-Code


S1AP-ServedPLMNs ::= SEQUENCE (SIZE(1.. s1ap-maxnoofPLMNsPerMME)) OF S1AP-PLMNidentity


S1AP-SubscriberProfileIDforRFP ::= INTEGER (1..256) 


S1AP-SupportedTAs ::= SEQUENCE (SIZE(1.. s1ap-maxnoofTACs)) OF S1AP-SupportedTAs-Item


S1AP-SupportedTAs-Item ::=        SEQUENCE  {
        tAC                                        S1AP-TAC,
        broadcastPLMNs                S1AP-BPLMNs,
        iE-Extensions                ProtocolExtensionContainer { {S1AP-SupportedTAs-Item-ExtIEs} } OPTIONAL,
        ...
}


S1AP-SupportedTAs-Item-ExtIEs S1AP-PROTOCOL-EXTENSION ::= {
        ...
}


S1AP-StratumLevel ::= INTEGER (0..3, ...)


S1AP-SynchronizationStatus ::= ENUMERATED { synchronous, asynchronous, ... }


S1AP-TimeSynchronizationInfo ::= SEQUENCE {
        stratumLevel                                        S1AP-StratumLevel,
        synchronizationStatus                        S1AP-SynchronizationStatus,
        iE-Extensions                                        ProtocolExtensionContainer { { S1AP-TimeSynchronizationInfo-ExtIEs} } OPTIONAL,
        ...
}


S1AP-TimeSynchronizationInfo-ExtIEs S1AP-PROTOCOL-EXTENSION ::= {
        ...
}


S1AP-S-TMSI ::= SEQUENCE {
        mMEC        S1AP-MME-Code,
        m-TMSI        S1AP-M-TMSI,
        iE-Extensions                ProtocolExtensionContainer { {S1AP-S-TMSI-ExtIEs} } OPTIONAL,
        ...
}


S1AP-S-TMSI-ExtIEs S1AP-PROTOCOL-EXTENSION ::= {
        ...
}


-- T


S1AP-TAC ::= OCTET STRING (SIZE (2))


S1AP-TAIListforWarning ::= SEQUENCE (SIZE(1..s1ap-maxnoofTAIforWarning)) OF S1AP-TAI


S1AP-TAI ::= SEQUENCE {
        pLMNidentity                        S1AP-PLMNidentity,
        tAC                                                S1AP-TAC,
        iE-Extensions                        ProtocolExtensionContainer { {S1AP-TAI-ExtIEs} } OPTIONAL,
        ...
}


S1AP-TAI-ExtIEs S1AP-PROTOCOL-EXTENSION ::= {
        ...
}


S1AP-TAI-Broadcast ::= SEQUENCE (SIZE(1..s1ap-maxnoofTAIforWarning)) OF S1AP-TAI-Broadcast-Item


S1AP-TAI-Broadcast-Item ::= SEQUENCE {
        tAI                                        S1AP-TAI,
        completedCellinTAI        S1AP-CompletedCellinTAI,
        iE-Extensions                ProtocolExtensionContainer { {S1AP-TAI-Broadcast-Item-ExtIEs} } OPTIONAL,
        ...
}


S1AP-TAI-Broadcast-Item-ExtIEs S1AP-PROTOCOL-EXTENSION ::= {
        ...
}


S1AP-TAI-Cancelled ::= SEQUENCE (SIZE(1..s1ap-maxnoofTAIforWarning)) OF S1AP-TAI-Cancelled-Item


S1AP-TAI-Cancelled-Item ::= SEQUENCE {
        tAI                                        S1AP-TAI,
        cancelledCellinTAI        S1AP-CancelledCellinTAI,
        iE-Extensions                ProtocolExtensionContainer { {S1AP-TAI-Cancelled-Item-ExtIEs} } OPTIONAL,
        ...
}


S1AP-TAI-Cancelled-Item-ExtIEs S1AP-PROTOCOL-EXTENSION ::= {
        ...
}


S1AP-TABasedMDT ::= SEQUENCE {
        tAListforMDT                        S1AP-TAListforMDT,
        iE-Extensions                        ProtocolExtensionContainer { {S1AP-TABasedMDT-ExtIEs} } OPTIONAL,
        ...
}


S1AP-TABasedMDT-ExtIEs S1AP-PROTOCOL-EXTENSION ::= {
        ...
}


S1AP-TAListforMDT ::= SEQUENCE (SIZE(1..s1ap-maxnoofTAforMDT)) OF S1AP-TAC


S1AP-CompletedCellinTAI ::= SEQUENCE (SIZE(1..s1ap-maxnoofCellinTAI)) OF S1AP-CompletedCellinTAI-Item


S1AP-CompletedCellinTAI-Item ::= SEQUENCE{
        eCGI                                S1AP-EUTRAN-CGI,
        iE-Extensions                ProtocolExtensionContainer { {S1AP-CompletedCellinTAI-Item-ExtIEs} } OPTIONAL,
        ...
}


S1AP-CompletedCellinTAI-Item-ExtIEs S1AP-PROTOCOL-EXTENSION ::= {
        ...
}


S1AP-TBCD-STRING ::= OCTET STRING (SIZE (3))


S1AP-TargetID ::= CHOICE {
        targeteNB-ID                        S1AP-TargeteNB-ID,
        targetRNC-ID                        S1AP-TargetRNC-ID,
        cGI                                                S1AP-CGI,
        ...
}


S1AP-TargeteNB-ID ::= SEQUENCE {
        global-S1AP-ENB-ID        S1AP-Global-ENB-ID,
        selected-S1AP-TAI        S1AP-TAI,
        iE-Extensions        ProtocolExtensionContainer { {S1AP-TargeteNB-ID-ExtIEs} } OPTIONAL,
        ...
}


S1AP-TargeteNB-ID-ExtIEs S1AP-PROTOCOL-EXTENSION ::= {
        ...
}


S1AP-TargetRNC-ID ::= SEQUENCE {
        lAI                                        S1AP-LAI,
        rAC                                        S1AP-RAC                 OPTIONAL,
        rNC-ID                                S1AP-RNC-ID,
        extendedRNC-ID                S1AP-ExtendedRNC-ID                OPTIONAL,
        iE-Extensions                ProtocolExtensionContainer { {S1AP-TargetRNC-ID-ExtIEs} } OPTIONAL,
        ...
        }




S1AP-TargetRNC-ID-ExtIEs S1AP-PROTOCOL-EXTENSION ::= {
        ...
}




S1AP-TargeteNB-ToSourceeNB-TransparentContainer                ::= SEQUENCE {
        rRC-Container                        S1AP-RRC-Container,
        iE-Extensions                        ProtocolExtensionContainer { {S1AP-TargeteNB-ToSourceeNB-TransparentContainer-ExtIEs} } OPTIONAL,
        ...
}


S1AP-TargeteNB-ToSourceeNB-TransparentContainer-ExtIEs S1AP-PROTOCOL-EXTENSION ::= {
        ...
}


S1AP-Target-ToSource-TransparentContainer ::= OCTET STRING
-- This IE includes a transparent container from the target RAN node to the source RAN node. 
-- The octets of the OCTET STRING are coded according to the specifications of the target system.


S1AP-TargetRNC-ToSourceRNC-TransparentContainer                ::= OCTET STRING
-- This is a dummy IE used only as a reference to the actual definition in relevant specification.


S1AP-TargetBSS-ToSourceBSS-TransparentContainer                ::= OCTET STRING
-- This is a dummy IE used only as a reference to the actual definition in relevant specification.


S1AP-ThresholdEventA2 ::= SEQUENCE { 
        measurementThreshold                S1AP-MeasurementThresholdA2,
        iE-Extensions                                ProtocolExtensionContainer { { S1AP-ThresholdEventA2-ExtIEs} } OPTIONAL,
        ...
}


S1AP-ThresholdEventA2-ExtIEs S1AP-PROTOCOL-EXTENSION ::= {
        ...
}


S1AP-Threshold-RSRP ::= INTEGER(0..97)


S1AP-Threshold-RSRQ ::= INTEGER(0..34)


S1AP-TimeToWait ::= ENUMERATED {v1s, v2s, v5s, v10s, v20s, v60s, ...}


S1AP-Time-UE-StayedInCell ::= INTEGER (0..4095)


S1AP-TransportLayerAddress                ::= BIT STRING (SIZE(1..160, ...))


S1AP-TraceActivation ::= SEQUENCE {
        e-UTRAN-Trace-ID                                        S1AP-E-UTRAN-Trace-ID,
        interfacesToTrace                                S1AP-InterfacesToTrace,
     traceDepth                                                S1AP-TraceDepth,
     traceCollectionEntityIPAddress        S1AP-TransportLayerAddress,
        iE-Extensions                                        ProtocolExtensionContainer { { S1AP-TraceActivation-ExtIEs} }                OPTIONAL,
        ...
}


S1AP-TraceActivation-ExtIEs S1AP-PROTOCOL-EXTENSION ::= {
-- Extension for Rel-10 to support MDT --
        { ID id-MDTConfiguration        CRITICALITY ignore        EXTENSION S1AP-MDT-Configuration                PRESENCE        optional },
        ...
}


S1AP-TraceDepth ::= ENUMERATED { 
        minimum,
        medium,
        maximum,
        minimumWithoutVendorSpecificExtension,
        mediumWithoutVendorSpecificExtension,
        maximumWithoutVendorSpecificExtension,
        ...
}


S1AP-E-UTRAN-Trace-ID ::=  OCTET STRING (SIZE (8))


S1AP-TrafficLoadReductionIndication ::= INTEGER (1..99)


S1AP-TypeOfError ::= ENUMERATED {
        not-understood,
        missing,
        ...
}


-- U


S1AP-UEAggregateMaximumBitrate ::= SEQUENCE {
        uEaggregateMaximumBitRateDL                                S1AP-BitRate,
        uEaggregateMaximumBitRateUL                                S1AP-BitRate,
        iE-Extensions                                                        ProtocolExtensionContainer { {S1AP-UEAggregate-MaximumBitrates-ExtIEs} } OPTIONAL,
        ...
}


S1AP-UEAggregate-MaximumBitrates-ExtIEs S1AP-PROTOCOL-EXTENSION ::= {
        ...
}






S1AP-UE-S1AP-IDs ::= CHOICE{
        uE-S1AP-ID-pair                S1AP-UE-S1AP-ID-pair,
        mME-UE-S1AP-ID                S1AP-MME-UE-S1AP-ID,
        ...
}


S1AP-UE-S1AP-ID-pair ::= SEQUENCE{
        mME-UE-S1AP-ID                S1AP-MME-UE-S1AP-ID,
        eNB-UE-S1AP-ID                S1AP-ENB-UE-S1AP-ID,
        iE-Extensions                ProtocolExtensionContainer { {S1AP-UE-S1AP-ID-pair-ExtIEs} } OPTIONAL,
        ...
}
S1AP-UE-S1AP-ID-pair-ExtIEs S1AP-PROTOCOL-EXTENSION ::= {
        ...
}




S1AP-UE-associatedLogicalS1-ConnectionItem ::= SEQUENCE {
        mME-UE-S1AP-ID                                        S1AP-MME-UE-S1AP-ID OPTIONAL,
        eNB-UE-S1AP-ID                                        S1AP-ENB-UE-S1AP-ID OPTIONAL,
        iE-Extensions                                        ProtocolExtensionContainer { { S1AP-UE-associatedLogicalS1-ConnectionItemExtIEs} } OPTIONAL,
        ...
}




S1AP-UE-associatedLogicalS1-ConnectionItemExtIEs S1AP-PROTOCOL-EXTENSION ::= {
        ...
}


S1AP-UEIdentityIndexValue        ::=        BIT STRING (SIZE (10))


S1AP-UE-HistoryInformation ::= SEQUENCE (SIZE(1..s1ap-maxnoofCells)) OF S1AP-LastVisitedCell-Item


S1AP-UEPagingID ::= CHOICE {
        s-TMSI                S1AP-S-TMSI,
        iMSI                S1AP-IMSI,
        ...
        }


S1AP-UERadioCapability ::= OCTET STRING


S1AP-UESecurityCapabilities ::= SEQUENCE {
        encryptionAlgorithms                        S1AP-EncryptionAlgorithms,
        integrityProtectionAlgorithms        S1AP-IntegrityProtectionAlgorithms,
        iE-Extensions                                        ProtocolExtensionContainer { { S1AP-UESecurityCapabilities-ExtIEs} }                OPTIONAL,
...
}


S1AP-UESecurityCapabilities-ExtIEs S1AP-PROTOCOL-EXTENSION ::= {
        ...
}


-- V
-- W


S1AP-WarningAreaList ::= CHOICE {
        cellIDList                                                S1AP-ECGIList,
        trackingAreaListforWarning                S1AP-TAIListforWarning,
        emergencyAreaIDList                                S1AP-EmergencyAreaIDList,
        ...
}




S1AP-WarningType ::= OCTET STRING (SIZE (2))


S1AP-WarningSecurityInfo ::= OCTET STRING (SIZE (50))




S1AP-WarningMessageContents ::= OCTET STRING (SIZE(1..9600))




-- X




S1AP-X2TNLConfigurationInfo ::= SEQUENCE {
        eNBX2TransportLayerAddresses        S1AP-ENBX2TLAs,
        iE-Extensions                                        ProtocolExtensionContainer { { S1AP-X2TNLConfigurationInfo-ExtIEs} } OPTIONAL,
        ...
}


S1AP-X2TNLConfigurationInfo-ExtIEs S1AP-PROTOCOL-EXTENSION ::= {
-- Extension for Release 10 to transfer the IPsec and U-plane addresses during ANR action --
        {ID id-eNBX2ExtendedTransportLayerAddresses        CRITICALITY ignore        EXTENSION S1AP-ENBX2ExtTLAs        PRESENCE optional},
        ...
}


S1AP-ENBX2ExtTLAs ::= SEQUENCE (SIZE(1.. s1ap-maxnoofeNBX2ExtTLAs)) OF S1AP-ENBX2ExtTLA


S1AP-ENBX2ExtTLA ::= SEQUENCE {
        iPsecTLA                                        S1AP-TransportLayerAddress                OPTIONAL,
        gTPTLAa                                                S1AP-ENBX2GTPTLAs                                OPTIONAL,
        iE-Extensions                                ProtocolExtensionContainer { { S1AP-ENBX2ExtTLA-ExtIEs} } OPTIONAL,
        ...
}


S1AP-ENBX2ExtTLA-ExtIEs S1AP-PROTOCOL-EXTENSION ::= {
        ...
}


S1AP-ENBX2GTPTLAs ::= SEQUENCE (SIZE(1.. s1ap-maxnoofeNBX2GTPTLAs)) OF S1AP-TransportLayerAddress


-- Y
-- Z


END




-- **************************************************************
--
-- Common definitions
--
-- **************************************************************


S1AP-CommonDataTypes {
itu-t (0) identified-organization (4) etsi (0) mobileDomain (0) 
eps-Access (21) modules (3) s1ap (1) version1 (1) s1ap-CommonDataTypes (3) }


DEFINITIONS AUTOMATIC TAGS ::= 


BEGIN


S1AP-Criticality                ::= ENUMERATED { reject, ignore, notify }


S1AP-Presence                ::= ENUMERATED { optional, conditional, mandatory }


S1AP-PrivateIE-ID        ::= CHOICE {
        local                                INTEGER (0..65535),
        global                                OBJECT IDENTIFIER
}


S1AP-ProcedureCode                ::= INTEGER  {
        id-HandoverPreparation(0),
        id-HandoverResourceAllocation(1),
        id-HandoverNotification(2),
        id-PathSwitchRequest(3),
        id-HandoverCancel(4),
        id-E-RABSetup(5),
        id-E-RABModify(6),
        id-E-RABRelease(7),
        id-E-RABReleaseIndication(8),
        id-InitialContextSetup(9),
        id-Paging(10),
        id-downlinkNASTransport(11),
        id-initialUEMessage(12),
        id-uplinkNASTransport(13),
        id-Reset(14),
        id-ErrorIndication(15),
        id-NASNonDeliveryIndication(16),
        id-S1Setup(17),
        id-UEContextReleaseRequest(18),
        id-DownlinkS1cdma2000tunneling(19),
        id-UplinkS1cdma2000tunneling(20),
        id-UEContextModification(21),
        id-UECapabilityInfoIndication(22),
        id-UEContextRelease(23),
        id-eNBStatusTransfer(24),
        id-MMEStatusTransfer(25),
        id-DeactivateTrace(26),
        id-TraceStart(27),
        id-TraceFailureIndication(28),
        id-ENBConfigurationUpdate(29),
        id-MMEConfigurationUpdate(30),
        id-LocationReportingControl(31),
        id-LocationReportingFailureIndication(32),
        id-LocationReport(33),
        id-OverloadStart(34),
        id-OverloadStop(35),
        id-WriteReplaceWarning(36),
        id-eNBDirectInformationTransfer(37),
        id-MMEDirectInformationTransfer(38),
        id-PrivateMessage(39),
        id-eNBConfigurationTransfer(40),
        id-MMEConfigurationTransfer(41),
        id-CellTrafficTrace(42),
        id-Kill(43),
        id-downlinkUEAssociatedLPPaTransport(44),
        id-uplinkUEAssociatedLPPaTransport(45),
        id-downlinkNonUEAssociatedLPPaTransport(46),
        id-uplinkNonUEAssociatedLPPaTransport(47)
} (0..255)


S1AP-ProtocolExtensionID        ::= INTEGER (0..65535)


S1AP-ProtocolIE-ID                ::= INTEGER {
        id-MME-UE-S1AP-ID(0),
        id-HandoverType(1),
        id-Cause(2),
        id-SourceID(3),
        id-TargetID(4),
        id-eNB-UE-S1AP-ID(8),
        id-E-RABSubjecttoDataForwardingList(12),
        id-E-RABtoReleaseListHOCmd(13),
        id-E-RABDataForwardingItem(14),
        id-E-RABReleaseItemBearerRelComp(15),
        id-E-RABToBeSetupListBearerSUReq(16),
        id-E-RABToBeSetupItemBearerSUReq(17),
        id-E-RABAdmittedList(18),
        id-E-RABFailedToSetupListHOReqAck(19),
        id-E-RABAdmittedItem(20),
        id-E-RABFailedtoSetupItemHOReqAck(21),
        id-E-RABToBeSwitchedDLList(22),
        id-E-RABToBeSwitchedDLItem(23),
        id-E-RABToBeSetupListCtxtSUReq(24),
        id-TraceActivation(25),
        id-NAS-PDU(26),
        id-E-RABToBeSetupItemHOReq(27),
        id-E-RABSetupListBearerSURes(28),
        id-E-RABFailedToSetupListBearerSURes(29),
        id-E-RABToBeModifiedListBearerModReq(30),
        id-E-RABModifyListBearerModRes(31),
        id-E-RABFailedToModifyList(32),
        id-E-RABToBeReleasedList(33),
        id-E-RABFailedToReleaseList(34),
        id-E-RABItem(35),
        id-E-RABToBeModifiedItemBearerModReq(36),
        id-E-RABModifyItemBearerModRes(37),
        id-E-RABReleaseItem(38),
        id-E-RABSetupItemBearerSURes(39),
        id-SecurityContext(40),
        id-HandoverRestrictionList(41),
        id-UEPagingID(43),
        id-pagingDRX(44),
        id-TAIList(46),
        id-TAIItem(47),
        id-E-RABFailedToSetupListCtxtSURes(48),
        id-E-RABReleaseItemHOCmd(49),
        id-E-RABSetupItemCtxtSURes(50),
        id-E-RABSetupListCtxtSURes(51),
        id-E-RABToBeSetupItemCtxtSUReq(52),
        id-E-RABToBeSetupListHOReq(53),
        id-GERANtoLTEHOInformationRes(55),
        id-UTRANtoLTEHOInformationRes(57),
        id-CriticalityDiagnostics(58),
        id-Global-ENB-ID(59),
        id-eNBname(60),
        id-MMEname(61),
        id-ServedPLMNs(63),
        id-SupportedTAs(64),
        id-TimeToWait(65),
        id-uEaggregateMaximumBitrate(66),
        id-TAI(67),
        id-E-RABReleaseListBearerRelComp(69),
        id-cdma2000PDU(70),
        id-cdma2000RATType(71),
        id-cdma2000SectorID(72),
        id-SecurityKey(73),
        id-UERadioCapability(74),
        id-GUMMEI-ID(75),
        id-E-RABInformationListItem(78),
        id-Direct-Forwarding-Path-Availability(79),
        id-UEIdentityIndexValue(80),
        id-cdma2000HOStatus(83),
        id-cdma2000HORequiredIndication(84),
        id-E-UTRAN-Trace-ID(86),
        id-RelativeMMECapacity(87),
        id-SourceMME-UE-S1AP-ID(88),
        id-Bearers-SubjectToStatusTransfer-Item(89),
        id-eNB-StatusTransfer-TransparentContainer(90),
        id-UE-associatedLogicalS1-ConnectionItem(91),
        id-ResetType(92),
        id-UE-associatedLogicalS1-ConnectionListResAck(93),
        id-E-RABToBeSwitchedULItem(94),
        id-E-RABToBeSwitchedULList(95),
        id-S-TMSI(96),
        id-cdma2000OneXRAND(97),
        id-RequestType(98),
        id-UE-S1AP-IDs(99),
        id-EUTRAN-CGI(100),
        id-OverloadResponse(101),
        id-cdma2000OneXSRVCCInfo(102),
        id-E-RABFailedToBeReleasedList(103),
        id-Source-ToTarget-TransparentContainer(104),
        id-ServedGUMMEIs(105),
        id-SubscriberProfileIDforRFP(106),
        id-UESecurityCapabilities(107),
        id-CSFallbackIndicator(108),
        id-CNDomain(109),
        id-E-RABReleasedList(110),
        id-MessageIdentifier(111),
        id-SerialNumber(112),
        id-WarningAreaList(113),
        id-RepetitionPeriod(114),
        id-NumberofBroadcastRequest(115),
        id-WarningType(116),
        id-WarningSecurityInfo(117),
        id-DataCodingScheme(118),
        id-WarningMessageContents(119),
        id-BroadcastCompletedAreaList(120),
        id-Inter-SystemInformationTransferTypeEDT(121),
        id-Inter-SystemInformationTransferTypeMDT(122),
        id-Target-ToSource-TransparentContainer(123),
        id-SRVCCOperationPossible(124),
        id-SRVCCHOIndication(125),
        id-NAS-DownlinkCount(126),
        id-CSG-Id(127),
        id-CSG-IdList(128),
        id-SONConfigurationTransferECT(129),
        id-SONConfigurationTransferMCT(130),
        id-TraceCollectionEntityIPAddress(131),
        id-MSClassmark2(132),
        id-MSClassmark3(133),
        id-RRC-Establishment-Cause(134),
        id-NASSecurityParametersfromE-UTRAN(135),
        id-NASSecurityParameterstoE-UTRAN(136),
        id-DefaultPagingDRX(137),
        id-Source-ToTarget-TransparentContainer-Secondary(138),
        id-Target-ToSource-TransparentContainer-Secondary(139),
        id-EUTRANRoundTripDelayEstimationInfo(140),
        id-BroadcastCancelledAreaList(141),
        id-ConcurrentWarningMessageIndicator(142),
        id-Data-Forwarding-Not-Possible(143),
        id-ExtendedRepetitionPeriod(144),
        id-CellAccessMode(145),
        id-CSGMembershipStatus(146),
        id-LPPa-PDU(147),
        id-Routing-ID(148),
        id-Time-Synchronization-Info(149),
        id-PS-ServiceNotAvailable(150),
        id-PagingPriority(151),
        id-x2TNLConfigurationInfo(152),
        id-eNBX2ExtendedTransportLayerAddresses(153),
        id-GUMMEIList(154),
        id-GW-TransportLayerAddress(155),
        id-Correlation-ID(156),
        id-SourceMME-GUMMEI(157),
        id-MME-UE-S1AP-ID-2(158),
        id-RegisteredLAI(159),
        id-RelayNode-Indicator(160),
        id-TrafficLoadReductionIndication(161),
        id-MDTConfiguration(162),
        id-MMERelaySupportIndicator(163),
        id-GWContextReleaseIndication(164),
        id-ManagementBasedMDTAllowed(165),
        id-PrivacyIndicator(166),
        id-GUMMEIType(170)

} (0..65535)


S1AP-TriggeringMessage        ::= ENUMERATED { initiating-message, successful-outcome, unsuccessfull-outcome }


END


-- **************************************************************
--
-- Constant definitions
--
-- **************************************************************


S1AP-Constants { 
itu-t (0) identified-organization (4) etsi (0) mobileDomain (0) 
eps-Access (21) modules (3) s1ap (1) version1 (1) s1ap-Constants (4) } 


DEFINITIONS AUTOMATIC TAGS ::= 


BEGIN


-- **************************************************************
--
-- IE parameter types from other modules.
--
-- **************************************************************


IMPORTS
        S1AP-ProcedureCode,
        S1AP-ProtocolIE-ID


FROM S1AP-CommonDataTypes;




-- **************************************************************
--
-- Elementary Procedures
--
-- **************************************************************


id-HandoverPreparation                                 S1AP-ProcedureCode ::= 0
id-HandoverResourceAllocation                 S1AP-ProcedureCode ::= 1
id-HandoverNotification                         S1AP-ProcedureCode ::= 2
id-PathSwitchRequest                                 S1AP-ProcedureCode ::= 3
id-HandoverCancel                                         S1AP-ProcedureCode ::= 4
id-E-RABSetup                                                S1AP-ProcedureCode ::= 5
id-E-RABModify                                                 S1AP-ProcedureCode ::= 6
id-E-RABRelease                                                S1AP-ProcedureCode ::= 7
id-E-RABReleaseIndication                        S1AP-ProcedureCode ::= 8
id-InitialContextSetup                                S1AP-ProcedureCode ::= 9
id-Paging                                                        S1AP-ProcedureCode ::= 10
id-downlinkNASTransport                                S1AP-ProcedureCode ::= 11
id-initialUEMessage                                        S1AP-ProcedureCode ::= 12
id-uplinkNASTransport                                S1AP-ProcedureCode ::= 13
id-Reset                                                        S1AP-ProcedureCode::= 14
id-ErrorIndication                                        S1AP-ProcedureCode ::= 15
id-NASNonDeliveryIndication                        S1AP-ProcedureCode ::= 16
id-S1Setup                                                        S1AP-ProcedureCode ::= 17
id-UEContextReleaseRequest                        S1AP-ProcedureCode ::= 18
id-DownlinkS1cdma2000tunneling                S1AP-ProcedureCode ::= 19
id-UplinkS1cdma2000tunneling                S1AP-ProcedureCode ::= 20
id-UEContextModification                        S1AP-ProcedureCode ::= 21
id-UECapabilityInfoIndication                S1AP-ProcedureCode ::= 22
id-UEContextRelease                                        S1AP-ProcedureCode ::= 23
id-eNBStatusTransfer                                S1AP-ProcedureCode ::= 24
id-MMEStatusTransfer                                S1AP-ProcedureCode ::= 25
id-DeactivateTrace                                        S1AP-ProcedureCode ::= 26
id-TraceStart                                                S1AP-ProcedureCode ::= 27
id-TraceFailureIndication                        S1AP-ProcedureCode ::= 28
id-ENBConfigurationUpdate                        S1AP-ProcedureCode ::= 29
id-MMEConfigurationUpdate                        S1AP-ProcedureCode ::= 30
id-LocationReportingControl                        S1AP-ProcedureCode ::= 31
id-LocationReportingFailureIndication        S1AP-ProcedureCode ::= 32
id-LocationReport                                        S1AP-ProcedureCode ::= 33
id-OverloadStart                                        S1AP-ProcedureCode ::= 34
id-OverloadStop                                                S1AP-ProcedureCode ::= 35
id-WriteReplaceWarning                                S1AP-ProcedureCode ::= 36
id-eNBDirectInformationTransfer                S1AP-ProcedureCode ::= 37
id-MMEDirectInformationTransfer                S1AP-ProcedureCode ::= 38
id-PrivateMessage                                        S1AP-ProcedureCode ::= 39
id-eNBConfigurationTransfer                        S1AP-ProcedureCode ::= 40
id-MMEConfigurationTransfer                        S1AP-ProcedureCode ::= 41
id-CellTrafficTrace                                        S1AP-ProcedureCode ::= 42
id-Kill                                                                S1AP-ProcedureCode ::= 43
id-downlinkUEAssociatedLPPaTransport        S1AP-ProcedureCode ::= 44
id-uplinkUEAssociatedLPPaTransport                S1AP-ProcedureCode ::= 45
id-downlinkNonUEAssociatedLPPaTransport        S1AP-ProcedureCode ::= 46
id-uplinkNonUEAssociatedLPPaTransport        S1AP-ProcedureCode ::= 47


-- **************************************************************
--
-- Extension constants
--
-- **************************************************************


s1ap-maxPrivateIEs                                                 INTEGER ::= 65535
s1ap-maxProtocolExtensions                                 INTEGER ::= 65535
s1ap-maxProtocolIEs                                                INTEGER ::= 65535
-- **************************************************************
--
-- Lists
--
-- **************************************************************


s1ap-maxNrOfCSGs                                                                INTEGER ::= 256
s1ap-maxNrOfE-RABs                                                        INTEGER ::= 256
s1ap-maxnoofTAIs                                                                INTEGER ::= 256
s1ap-maxnoofTACs                                                                INTEGER ::= 256
s1ap-maxNrOfErrors                                                        INTEGER ::= 256
s1ap-maxnoofBPLMNs                                                        INTEGER ::= 6
s1ap-maxnoofPLMNsPerMME                                                INTEGER ::= 32
s1ap-maxnoofEPLMNs                                                        INTEGER ::= 15
s1ap-maxnoofEPLMNsPlusOne                                        INTEGER ::= 16
s1ap-maxnoofForbLACs                                                        INTEGER ::= 4096
s1ap-maxnoofForbTACs                                                        INTEGER ::= 4096
s1ap-maxNrOfIndividualS1ConnectionsToReset        INTEGER ::= 256
s1ap-maxnoofCells                                                        INTEGER ::= 16
s1ap-maxnoofTAIforWarning                                        INTEGER ::= 65535 
s1ap-maxnoofCellID                                                        INTEGER ::= 65535 
s1ap-maxnoofEmergencyAreaID                                        INTEGER ::= 65535 
s1ap-maxnoofCellinTAI                                                INTEGER ::= 65535 
s1ap-maxnoofCellinEAI                                                INTEGER ::= 65535 
s1ap-maxnoofeNBX2TLAs                                                INTEGER ::= 2
s1ap-maxnoofeNBX2ExtTLAs                                                INTEGER ::= 16
s1ap-maxnoofeNBX2GTPTLAs                                                INTEGER ::= 16
s1ap-maxnoofRATs                                                                INTEGER ::= 8
s1ap-maxnoofGroupIDs                                                        INTEGER ::= 65535
s1ap-maxnoofMMECs                                                        INTEGER ::= 256
s1ap-maxnoofCellIDforMDT                                                INTEGER ::= 32
s1ap-maxnoofTAforMDT                                                        INTEGER ::= 8




-- **************************************************************
--
-- IEs
--
-- **************************************************************


id-MME-UE-S1AP-ID                                                        S1AP-ProtocolIE-ID ::= 0
id-HandoverType                                                                S1AP-ProtocolIE-ID ::= 1
id-Cause                                                                        S1AP-ProtocolIE-ID ::= 2
id-SourceID                                                                        S1AP-ProtocolIE-ID ::= 3
id-TargetID                                                                        S1AP-ProtocolIE-ID ::= 4
id-eNB-UE-S1AP-ID                                                        S1AP-ProtocolIE-ID ::= 8
id-E-RABSubjecttoDataForwardingList                        S1AP-ProtocolIE-ID ::= 12
id-E-RABtoReleaseListHOCmd                                        S1AP-ProtocolIE-ID ::= 13
id-E-RABDataForwardingItem                                        S1AP-ProtocolIE-ID ::= 14
id-E-RABReleaseItemBearerRelComp                        S1AP-ProtocolIE-ID ::= 15
id-E-RABToBeSetupListBearerSUReq                        S1AP-ProtocolIE-ID ::= 16
id-E-RABToBeSetupItemBearerSUReq                        S1AP-ProtocolIE-ID ::= 17
id-E-RABAdmittedList                                                S1AP-ProtocolIE-ID ::= 18
id-E-RABFailedToSetupListHOReqAck                        S1AP-ProtocolIE-ID ::= 19
id-E-RABAdmittedItem                                                S1AP-ProtocolIE-ID ::= 20
id-E-RABFailedtoSetupItemHOReqAck                        S1AP-ProtocolIE-ID ::= 21
id-E-RABToBeSwitchedDLList                                        S1AP-ProtocolIE-ID ::= 22
id-E-RABToBeSwitchedDLItem                                        S1AP-ProtocolIE-ID ::= 23
id-E-RABToBeSetupListCtxtSUReq                                S1AP-ProtocolIE-ID ::= 24
id-TraceActivation                                                        S1AP-ProtocolIE-ID ::= 25
id-NAS-PDU                                                                        S1AP-ProtocolIE-ID ::= 26
id-E-RABToBeSetupItemHOReq                                        S1AP-ProtocolIE-ID ::= 27
id-E-RABSetupListBearerSURes                                S1AP-ProtocolIE-ID ::= 28
id-E-RABFailedToSetupListBearerSURes                S1AP-ProtocolIE-ID ::= 29
id-E-RABToBeModifiedListBearerModReq                S1AP-ProtocolIE-ID ::= 30
id-E-RABModifyListBearerModRes                                S1AP-ProtocolIE-ID ::= 31
id-E-RABFailedToModifyList                                        S1AP-ProtocolIE-ID ::= 32
id-E-RABToBeReleasedList                                        S1AP-ProtocolIE-ID ::= 33
id-E-RABFailedToReleaseList                                        S1AP-ProtocolIE-ID ::= 34
id-E-RABItem                                                                S1AP-ProtocolIE-ID ::= 35
id-E-RABToBeModifiedItemBearerModReq                S1AP-ProtocolIE-ID ::= 36
id-E-RABModifyItemBearerModRes                                S1AP-ProtocolIE-ID ::= 37
id-E-RABReleaseItem                                                        S1AP-ProtocolIE-ID ::= 38
id-E-RABSetupItemBearerSURes                                S1AP-ProtocolIE-ID ::= 39
id-SecurityContext                                                        S1AP-ProtocolIE-ID ::= 40
id-HandoverRestrictionList                                        S1AP-ProtocolIE-ID ::= 41
id-UEPagingID                                                                 S1AP-ProtocolIE-ID ::= 43
id-pagingDRX                                                                 S1AP-ProtocolIE-ID ::= 44
id-TAIList                                                                        S1AP-ProtocolIE-ID ::= 46
id-TAIItem                                                                        S1AP-ProtocolIE-ID ::= 47
id-E-RABFailedToSetupListCtxtSURes                        S1AP-ProtocolIE-ID ::= 48
id-E-RABReleaseItemHOCmd                                        S1AP-ProtocolIE-ID ::= 49
id-E-RABSetupItemCtxtSURes                                        S1AP-ProtocolIE-ID ::= 50
id-E-RABSetupListCtxtSURes                                        S1AP-ProtocolIE-ID ::= 51
id-E-RABToBeSetupItemCtxtSUReq                                S1AP-ProtocolIE-ID ::= 52
id-E-RABToBeSetupListHOReq                                        S1AP-ProtocolIE-ID ::= 53
id-GERANtoLTEHOInformationRes                                        S1AP-ProtocolIE-ID ::= 55
id-UTRANtoLTEHOInformationRes                                        S1AP-ProtocolIE-ID ::= 57
id-CriticalityDiagnostics                                                 S1AP-ProtocolIE-ID ::= 58
id-Global-ENB-ID                                                                S1AP-ProtocolIE-ID ::= 59
id-eNBname                                                                                S1AP-ProtocolIE-ID ::= 60
id-MMEname                                                                                S1AP-ProtocolIE-ID ::= 61
id-ServedPLMNs                                                                        S1AP-ProtocolIE-ID ::= 63
id-SupportedTAs                                                                        S1AP-ProtocolIE-ID ::= 64
id-TimeToWait                                                                        S1AP-ProtocolIE-ID ::= 65
id-uEaggregateMaximumBitrate                                        S1AP-ProtocolIE-ID ::= 66
id-TAI                                                                                        S1AP-ProtocolIE-ID ::= 67
id-E-RABReleaseListBearerRelComp                                S1AP-ProtocolIE-ID ::= 69
id-cdma2000PDU                                                                        S1AP-ProtocolIE-ID ::= 70
id-cdma2000RATType                                                                S1AP-ProtocolIE-ID ::= 71
id-cdma2000SectorID                                                                S1AP-ProtocolIE-ID ::= 72
id-SecurityKey                                                                        S1AP-ProtocolIE-ID ::= 73
id-UERadioCapability                                                        S1AP-ProtocolIE-ID ::= 74
id-GUMMEI-ID                                                                        S1AP-ProtocolIE-ID ::= 75
id-E-RABInformationListItem                                                S1AP-ProtocolIE-ID ::= 78
id-Direct-Forwarding-Path-Availability                        S1AP-ProtocolIE-ID ::= 79
id-UEIdentityIndexValue                                                        S1AP-ProtocolIE-ID ::= 80
id-cdma2000HOStatus                                                                S1AP-ProtocolIE-ID ::= 83
id-cdma2000HORequiredIndication                                        S1AP-ProtocolIE-ID ::= 84
id-E-UTRAN-Trace-ID                                                                S1AP-ProtocolIE-ID ::= 86
id-RelativeMMECapacity                                                        S1AP-ProtocolIE-ID ::= 87
id-SourceMME-UE-S1AP-ID                                                        S1AP-ProtocolIE-ID ::= 88
id-Bearers-SubjectToStatusTransfer-Item                        S1AP-ProtocolIE-ID ::= 89
id-eNB-StatusTransfer-TransparentContainer                S1AP-ProtocolIE-ID ::= 90
id-UE-associatedLogicalS1-ConnectionItem                S1AP-ProtocolIE-ID ::= 91
id-ResetType                                                                        S1AP-ProtocolIE-ID ::= 92
id-UE-associatedLogicalS1-ConnectionListResAck        S1AP-ProtocolIE-ID ::= 93
id-E-RABToBeSwitchedULItem                                                S1AP-ProtocolIE-ID ::= 94
id-E-RABToBeSwitchedULList                                                S1AP-ProtocolIE-ID ::= 95
id-S-TMSI                                                                                S1AP-ProtocolIE-ID ::= 96
id-cdma2000OneXRAND                                                                S1AP-ProtocolIE-ID ::= 97
id-RequestType                                                                        S1AP-ProtocolIE-ID ::= 98
id-UE-S1AP-IDs                                                                        S1AP-ProtocolIE-ID ::= 99
id-EUTRAN-CGI                                                                        S1AP-ProtocolIE-ID ::= 100
id-OverloadResponse                                                                S1AP-ProtocolIE-ID ::= 101
id-cdma2000OneXSRVCCInfo                                                S1AP-ProtocolIE-ID ::= 102
id-E-RABFailedToBeReleasedList                                        S1AP-ProtocolIE-ID ::= 103
id-Source-ToTarget-TransparentContainer                        S1AP-ProtocolIE-ID ::= 104
id-ServedGUMMEIs                                                                S1AP-ProtocolIE-ID ::= 105
id-SubscriberProfileIDforRFP                                        S1AP-ProtocolIE-ID ::= 106
id-UESecurityCapabilities                                                S1AP-ProtocolIE-ID ::= 107
id-CSFallbackIndicator                                                        S1AP-ProtocolIE-ID ::= 108
id-CNDomain                                                                                S1AP-ProtocolIE-ID ::= 109
id-E-RABReleasedList                                                        S1AP-ProtocolIE-ID ::= 110
id-MessageIdentifier                                                        S1AP-ProtocolIE-ID ::= 111
id-SerialNumber                                                                        S1AP-ProtocolIE-ID ::= 112
id-WarningAreaList                                                                S1AP-ProtocolIE-ID ::= 113
id-RepetitionPeriod                                                                S1AP-ProtocolIE-ID ::= 114
id-NumberofBroadcastRequest                                                S1AP-ProtocolIE-ID ::= 115
id-WarningType                                                                        S1AP-ProtocolIE-ID ::= 116
id-WarningSecurityInfo                                                        S1AP-ProtocolIE-ID ::= 117
id-DataCodingScheme                                                                S1AP-ProtocolIE-ID ::= 118
id-WarningMessageContents                                                S1AP-ProtocolIE-ID ::= 119
id-BroadcastCompletedAreaList                                        S1AP-ProtocolIE-ID ::= 120
id-Inter-SystemInformationTransferTypeEDT                S1AP-ProtocolIE-ID ::= 121
id-Inter-SystemInformationTransferTypeMDT                S1AP-ProtocolIE-ID ::= 122
id-Target-ToSource-TransparentContainer                        S1AP-ProtocolIE-ID ::= 123
id-SRVCCOperationPossible                                                S1AP-ProtocolIE-ID ::= 124
id-SRVCCHOIndication                                                        S1AP-ProtocolIE-ID ::= 125
id-NAS-DownlinkCount                                                        S1AP-ProtocolIE-ID ::= 126
id-CSG-Id                                                                                S1AP-ProtocolIE-ID ::= 127
id-CSG-IdList                                                                        S1AP-ProtocolIE-ID ::= 128
id-SONConfigurationTransferECT                                        S1AP-ProtocolIE-ID ::= 129
id-SONConfigurationTransferMCT                                        S1AP-ProtocolIE-ID ::= 130
id-TraceCollectionEntityIPAddress                                S1AP-ProtocolIE-ID ::= 131
id-MSClassmark2                                                                        S1AP-ProtocolIE-ID ::= 132
id-MSClassmark3                                                                        S1AP-ProtocolIE-ID ::= 133
id-RRC-Establishment-Cause                                                S1AP-ProtocolIE-ID ::= 134
id-NASSecurityParametersfromE-UTRAN                                S1AP-ProtocolIE-ID ::= 135
id-NASSecurityParameterstoE-UTRAN                                S1AP-ProtocolIE-ID ::= 136
id-DefaultPagingDRX                                                                S1AP-ProtocolIE-ID ::= 137
id-Source-ToTarget-TransparentContainer-Secondary        S1AP-ProtocolIE-ID ::= 138
id-Target-ToSource-TransparentContainer-Secondary        S1AP-ProtocolIE-ID ::= 139
id-EUTRANRoundTripDelayEstimationInfo                        S1AP-ProtocolIE-ID ::= 140
id-BroadcastCancelledAreaList                                        S1AP-ProtocolIE-ID ::= 141
id-ConcurrentWarningMessageIndicator                        S1AP-ProtocolIE-ID ::= 142
id-Data-Forwarding-Not-Possible                                        S1AP-ProtocolIE-ID ::= 143
id-ExtendedRepetitionPeriod                                                S1AP-ProtocolIE-ID ::= 144
id-CellAccessMode                                                                S1AP-ProtocolIE-ID ::= 145
id-CSGMembershipStatus                                                         S1AP-ProtocolIE-ID ::= 146
id-LPPa-PDU                                                                                S1AP-ProtocolIE-ID ::= 147
id-Routing-ID                                                                        S1AP-ProtocolIE-ID ::= 148
id-Time-Synchronization-Info                                        S1AP-ProtocolIE-ID ::= 149
id-PS-ServiceNotAvailable                                                S1AP-ProtocolIE-ID ::= 150
id-PagingPriority                                                                S1AP-ProtocolIE-ID ::= 151
id-x2TNLConfigurationInfo                                                S1AP-ProtocolIE-ID ::= 152
id-eNBX2ExtendedTransportLayerAddresses                        S1AP-ProtocolIE-ID ::= 153
id-GUMMEIList                                                                        S1AP-ProtocolIE-ID ::= 154
id-GW-TransportLayerAddress                                                S1AP-ProtocolIE-ID ::= 155
id-Correlation-ID                                                                S1AP-ProtocolIE-ID ::= 156
id-SourceMME-GUMMEI                                                                S1AP-ProtocolIE-ID ::= 157
id-MME-UE-S1AP-ID-2                                                                S1AP-ProtocolIE-ID ::= 158
id-RegisteredLAI                                                                S1AP-ProtocolIE-ID ::= 159
id-RelayNode-Indicator                                                        S1AP-ProtocolIE-ID ::= 160
id-TrafficLoadReductionIndication                                S1AP-ProtocolIE-ID ::= 161
id-MDTConfiguration                                                                S1AP-ProtocolIE-ID ::= 162
id-MMERelaySupportIndicator                                                S1AP-ProtocolIE-ID ::= 163
id-GWContextReleaseIndication                                        S1AP-ProtocolIE-ID ::= 164
id-ManagementBasedMDTAllowed                                        S1AP-ProtocolIE-ID ::= 165
id-PrivacyIndicator                                                                S1AP-ProtocolIE-ID ::= 166
id-GUMMEIType										S1ap-S1AP-ProtocolIE-ID ::= 170


END


-- **************************************************************
--
-- Container definitions
--
-- **************************************************************


S1AP-Containers {
itu-t (0) identified-organization (4) etsi (0) mobileDomain (0) 
eps-Access (21) modules (3) s1ap (1) version1 (1) s1ap-Containers (5) }


DEFINITIONS AUTOMATIC TAGS ::= 


BEGIN


-- **************************************************************
--
-- IE parameter types from other modules.
--
-- **************************************************************


IMPORTS
        S1AP-Criticality,
        S1AP-Presence,
        S1AP-PrivateIE-ID,
        S1AP-ProtocolExtensionID,
        S1AP-ProtocolIE-ID
FROM S1AP-CommonDataTypes


        s1ap-maxPrivateIEs,
        s1ap-maxProtocolExtensions,
        s1ap-maxProtocolIEs,
        s1ap-maxNrOfE-RABs
FROM S1AP-Constants;


-- **************************************************************
--
-- Class Definition for Protocol IEs
--
-- **************************************************************


S1AP-PROTOCOL-IES ::= CLASS {
        &id                                S1AP-ProtocolIE-ID                                         UNIQUE,
        &criticality                        S1AP-Criticality,
        &Value,
        &presence                        S1AP-Presence
}
WITH SYNTAX {
        ID                                &id
        CRITICALITY                        &criticality
        TYPE                                &Value
        PRESENCE                        &presence
}


-- **************************************************************
--
-- Class Definition for Protocol IEs
--
-- **************************************************************


S1AP-PROTOCOL-IES-PAIR ::= CLASS {
        &id                                S1AP-ProtocolIE-ID                                         UNIQUE,
        &firstCriticality                S1AP-Criticality,
        &FirstValue,
        &secondCriticality                S1AP-Criticality,
        &SecondValue,
        &presence                        S1AP-Presence
}
WITH SYNTAX {
        ID                                &id
        FIRST CRITICALITY                 &firstCriticality
        FIRST TYPE                        &FirstValue
        SECOND CRITICALITY                 &secondCriticality
        SECOND TYPE                        &SecondValue
        PRESENCE                        &presence
}


-- **************************************************************
--
-- Class Definition for Protocol Extensions
--
-- **************************************************************


S1AP-PROTOCOL-EXTENSION ::= CLASS {
        &id                                S1AP-ProtocolExtensionID                                 UNIQUE,
        &criticality                        S1AP-Criticality,
        &Extension,
        &presence                S1AP-Presence
}
WITH SYNTAX {
        ID                                &id
        CRITICALITY                        &criticality
        EXTENSION                        &Extension
        PRESENCE                &presence
}


-- **************************************************************
--
-- Class Definition for Private IEs
--
-- **************************************************************


S1AP-PRIVATE-IES ::= CLASS {
        &id                                S1AP-PrivateIE-ID,
        &criticality                        S1AP-Criticality,
        &Value,
        &presence                S1AP-Presence
}
WITH SYNTAX {
        ID                                &id
        CRITICALITY                        &criticality
        TYPE                        &Value
        PRESENCE                &presence
}


-- **************************************************************
--
-- Container for Protocol IEs
--
-- **************************************************************


ProtocolIE-Container {S1AP-PROTOCOL-IES : IEsSetParam} ::= 
        SEQUENCE (SIZE (0..s1ap-maxProtocolIEs)) OF
        ProtocolIE-Field {{IEsSetParam}}


ProtocolIE-SingleContainer {S1AP-PROTOCOL-IES : IEsSetParam} ::= 
        ProtocolIE-Field {{IEsSetParam}}


ProtocolIE-Field {S1AP-PROTOCOL-IES : IEsSetParam} ::= SEQUENCE {
        id                                S1AP-PROTOCOL-IES.&id                                ({IEsSetParam}),
        criticality                        S1AP-PROTOCOL-IES.&criticality                        ({IEsSetParam}{@id}),
        value                                S1AP-PROTOCOL-IES.&Value                        ({IEsSetParam}{@id})
}


-- **************************************************************
--
-- Container for Protocol IE Pairs
--
-- **************************************************************


ProtocolIE-ContainerPair {S1AP-PROTOCOL-IES-PAIR : IEsSetParam} ::= 
        SEQUENCE (SIZE (0..s1ap-maxProtocolIEs)) OF
        ProtocolIE-FieldPair {{IEsSetParam}}


ProtocolIE-FieldPair {S1AP-PROTOCOL-IES-PAIR : IEsSetParam} ::= SEQUENCE {
        id                                S1AP-PROTOCOL-IES-PAIR.&id                        ({IEsSetParam}),
        firstCriticality                S1AP-PROTOCOL-IES-PAIR.&firstCriticality        ({IEsSetParam}{@id}),
        firstValue                        S1AP-PROTOCOL-IES-PAIR.&FirstValue                ({IEsSetParam}{@id}),
        secondCriticality                S1AP-PROTOCOL-IES-PAIR.&secondCriticality        ({IEsSetParam}{@id}),
        secondValue                        S1AP-PROTOCOL-IES-PAIR.&SecondValue                ({IEsSetParam}{@id})
}


-- **************************************************************
--
-- Container Lists for Protocol IE Containers
--
-- **************************************************************


ProtocolIE-ContainerList {INTEGER : lowerBound, INTEGER : upperBound, S1AP-PROTOCOL-IES : IEsSetParam} ::=
        SEQUENCE (SIZE (lowerBound..upperBound)) OF
        ProtocolIE-SingleContainer {{IEsSetParam}}


ProtocolIE-ContainerPairList {INTEGER : lowerBound, INTEGER : upperBound, S1AP-PROTOCOL-IES-PAIR : IEsSetParam} ::=
        SEQUENCE (SIZE (lowerBound..upperBound)) OF
        ProtocolIE-ContainerPair {{IEsSetParam}}


-- **************************************************************
--
-- Container for Protocol Extensions
--
-- **************************************************************


ProtocolExtensionContainer {S1AP-PROTOCOL-EXTENSION : ExtensionSetParam} ::= 
        SEQUENCE (SIZE (1..s1ap-maxProtocolExtensions)) OF
        ProtocolExtensionField {{ExtensionSetParam}}


ProtocolExtensionField {S1AP-PROTOCOL-EXTENSION : ExtensionSetParam} ::= SEQUENCE {
        id                                S1AP-PROTOCOL-EXTENSION.&id                        ({ExtensionSetParam}),
        criticality                        S1AP-PROTOCOL-EXTENSION.&criticality                ({ExtensionSetParam}{@id}),
        extensionValue                        S1AP-PROTOCOL-EXTENSION.&Extension                ({ExtensionSetParam}{@id})
}


-- **************************************************************
--
-- Container for Private IEs
--
-- **************************************************************


PrivateIE-Container {S1AP-PRIVATE-IES : IEsSetParam } ::= 
        SEQUENCE (SIZE (1.. s1ap-maxPrivateIEs)) OF
        PrivateIE-Field {{IEsSetParam}}


PrivateIE-Field {S1AP-PRIVATE-IES : IEsSetParam} ::= SEQUENCE {
        id                                S1AP-PRIVATE-IES.&id                        ({IEsSetParam}),
        criticality                        S1AP-PRIVATE-IES.&criticality                ({IEsSetParam}{@id}),
        value                        S1AP-PRIVATE-IES.&Value                ({IEsSetParam}{@id})
}


END


-- **************************************************************
--
-- for S1ap-IE
--
-- **************************************************************

S1AP-PDU {
    itu-t (0) identified-organization (4) etsi (0) mobileDomain (0)
    eps-Access (21) modules (3) s1ap (1) version1 (1)
}

DEFINITIONS AUTOMATIC TAGS ::=

BEGIN

IMPORTS
    S1AP-Criticality,
    S1AP-ProtocolIE-ID

FROM S1AP-CommonDataTypes;

S1AP-IE ::= SEQUENCE {
    id          S1AP-ProtocolIE-ID,
    criticality S1AP-Criticality,
    value       ANY
}

END
